--
-- V1600G.my
-- MIB generated by MG-SOFT Visual MIB Builder Version 6.0  Build 88
-- Thursday, April 03, 2025 at 11:12:10
--

--  V1600G.my
-- MIB generated by MG-SOFT Visual MIB Builder Version 6.0  Build 88
-- Friday, October 25, 2024 at 10:04:05
-- 
--  V1600D.my
-- MIB generated by MG-SOFT Visual MIB Builder Version 6.0  Build 88
-- Tuesday, September 01, 2015 at 08:41:32
-- 

	V1600G DEFINITIONS ::= BEGIN
 
		IMPORTS
			enterprises, IpAddress, Integer32, Unsigned32, Counter64, 
			OBJECT-TYPE			
				FROM SNMPv2-SMI;
	
	
--
-- Node definitions
--
	
--  Node definitions
-- 
-- Node definitions
-- 
-- 1.3.6.1.4.1.37950
-- 1.3.6.1.4.1.37950
		-- 1.3.6.1.4.1.37950
		vsolution OBJECT IDENTIFIER ::= { enterprises 37950 }

		
--   1.3.6.1.4.1.37950.1
-- 1.3.6.1.4.1.37950.1
		-- 1.3.6.1.4.1.37950.1
		business OBJECT IDENTIFIER ::= { vsolution 1 }

		
--   1.3.6.1.4.1.37950.1.1
-- 1.3.6.1.4.1.37950.1.1
		-- 1.3.6.1.4.1.37950.1.1
		devices OBJECT IDENTIFIER ::= { business 1 }

		
--  1.3.6.1.4.1.37950.1.1.6
		-- 1.3.6.1.4.1.37950.1.1.6
		v1600g OBJECT IDENTIFIER ::= { devices 6 }

		
--  1.3.6.1.4.1.37950.1.1.6.1
		-- 1.3.6.1.4.1.37950.1.1.6.1
		v1600gOnu OBJECT IDENTIFIER ::= { v1600g 1 }

		
--  1.3.6.1.4.1.37950.1.1.6.1.1
		-- 1.3.6.1.4.1.37950.1.1.6.1.1
		gOnuAuthList OBJECT IDENTIFIER ::= { v1600gOnu 1 }

		
--  1.3.6.1.4.1.37950.1.1.6.1.1.1
		-- 1.3.6.1.4.1.37950.1.1.6.1.1.1
		gOnuStaInfoTable OBJECT-TYPE
			SYNTAX SEQUENCE OF GOnuStaInfoEntry
			MAX-ACCESS not-accessible
			STATUS current
			DESCRIPTION
				"Description."
			::= { gOnuAuthList 1 }

		
--  1.3.6.1.4.1.37950.1.1.6.1.1.1.1
		-- 1.3.6.1.4.1.37950.1.1.6.1.1.1.1
		gOnuStaInfoEntry OBJECT-TYPE
			SYNTAX GOnuStaInfoEntry
			MAX-ACCESS not-accessible
			STATUS current
			DESCRIPTION
				"Description."
			INDEX { gOnuStaInfoPonInx, gOnuStaInfoOnuInx }
			::= { gOnuStaInfoTable 1 }

		
		GOnuStaInfoEntry ::=
			SEQUENCE { 
				gOnuStaInfoPonInx
					INTEGER,
				gOnuStaInfoOnuInx
					INTEGER,
				gOnuStaInfoAdminSta
					INTEGER,
				gOnuStaInfoOmccSta
					INTEGER,
				gOnuStaInfoPhaseSta
					INTEGER,
				gOnuStaInfoSlotInx
					INTEGER,
				gOnuStaInfoDesc
					OCTET STRING,
				gOnuStaInfoLastRegisterTime
					OCTET STRING,
				gOnuStaInfoLastDeregisterTime
					OCTET STRING,
				gOnuStaInfoLastDeregisterReason
					OCTET STRING,
				gOnuStaInfoAliveTime
					OCTET STRING
			 }

--  1.3.6.1.4.1.37950.1.1.6.1.1.1.1.1
		-- 1.3.6.1.4.1.37950.1.1.6.1.1.1.1.1
		gOnuStaInfoPonInx OBJECT-TYPE
			SYNTAX INTEGER (1..16)
			MAX-ACCESS read-only
			STATUS current
			DESCRIPTION
				"Description."
			::= { gOnuStaInfoEntry 1 }

		
--  1.3.6.1.4.1.37950.1.1.6.1.1.1.1.2
		-- 1.3.6.1.4.1.37950.1.1.6.1.1.1.1.2
		gOnuStaInfoOnuInx OBJECT-TYPE
			SYNTAX INTEGER (1..128)
			MAX-ACCESS read-only
			STATUS current
			DESCRIPTION
				"Description."
			::= { gOnuStaInfoEntry 2 }

		
--  1.3.6.1.4.1.37950.1.1.6.1.1.1.1.3
		-- 1.3.6.1.4.1.37950.1.1.6.1.1.1.1.3
		gOnuStaInfoAdminSta OBJECT-TYPE
			SYNTAX INTEGER
				{
				enable(1),
				disable(2)
				}
			MAX-ACCESS read-only
			STATUS current
			DESCRIPTION
				"Description."
			::= { gOnuStaInfoEntry 3 }

		
--  1.3.6.1.4.1.37950.1.1.6.1.1.1.1.4
		-- 1.3.6.1.4.1.37950.1.1.6.1.1.1.1.4
		gOnuStaInfoOmccSta OBJECT-TYPE
			SYNTAX INTEGER
				{
				enable(1),
				disable(2)
				}
			MAX-ACCESS read-only
			STATUS current
			DESCRIPTION
				"Description."
			::= { gOnuStaInfoEntry 4 }

		
--  1.3.6.1.4.1.37950.1.1.6.1.1.1.1.5
		-- 1.3.6.1.4.1.37950.1.1.6.1.1.1.1.5
		gOnuStaInfoPhaseSta OBJECT-TYPE
			SYNTAX INTEGER
				{
				logging(0),
				los(1),
				syncMib(2),
				working(3),
				dyingGasp(4),
				authFail(5),
				offLine(6),
				deactivated(7),
				configFail(8)
				}
			MAX-ACCESS read-only
			STATUS current
			DESCRIPTION
				"Description."
			::= { gOnuStaInfoEntry 5 }

		
--           1.3.6.1.4.1.37950.1.1.6.1.1.1.1.6
-- 1.3.6.1.4.1.37950.1.1.6.1.1.1.1.6
-- 1.3.6.1.4.1.37950.1.1.6.1.1.1.1.6
-- 1.3.6.1.4.1.37950.1.1.6.1.1.1.1.6
-- 1.3.6.1.4.1.37950.1.1.6.1.1.1.1.6
-- 1.3.6.1.4.1.37950.1.1.6.1.1.1.1.6
-- 1.3.6.1.4.1.37950.1.1.6.1.1.1.1.6
-- 1.3.6.1.4.1.37950.1.1.6.1.1.1.1.6
-- 1.3.6.1.4.1.37950.1.1.6.1.1.1.1.6
-- 1.3.6.1.4.1.37950.1.1.6.1.1.1.1.6
		-- 1.3.6.1.4.1.37950.1.1.6.1.1.1.1.6
		gOnuStaInfoSlotInx OBJECT-TYPE
			SYNTAX INTEGER (0..4)
			MAX-ACCESS read-only
			STATUS current
			DESCRIPTION
				"Description."
			::= { gOnuStaInfoEntry 6 }

		
--  1.3.6.1.4.1.37950.1.1.6.1.1.1.1.7
		-- 1.3.6.1.4.1.37950.1.1.6.1.1.1.1.7
		gOnuStaInfoDesc OBJECT-TYPE
			SYNTAX OCTET STRING
			MAX-ACCESS read-only
			STATUS current
			DESCRIPTION
				"Description."
			::= { gOnuStaInfoEntry 7 }

		
--  1.3.6.1.4.1.37950.1.1.6.1.1.1.1.8
		-- 1.3.6.1.4.1.37950.1.1.6.1.1.1.1.8
		gOnuStaInfoLastRegisterTime OBJECT-TYPE
			SYNTAX OCTET STRING
			MAX-ACCESS read-only
			STATUS current
			DESCRIPTION
				"Description."
			::= { gOnuStaInfoEntry 8 }

		
--  1.3.6.1.4.1.37950.1.1.6.1.1.1.1.9
		-- 1.3.6.1.4.1.37950.1.1.6.1.1.1.1.9
		gOnuStaInfoLastDeregisterTime OBJECT-TYPE
			SYNTAX OCTET STRING
			MAX-ACCESS read-only
			STATUS current
			DESCRIPTION
				"Description."
			::= { gOnuStaInfoEntry 9 }

		
--  1.3.6.1.4.1.37950.1.1.6.1.1.1.1.10
		-- 1.3.6.1.4.1.37950.1.1.6.1.1.1.1.10
		gOnuStaInfoLastDeregisterReason OBJECT-TYPE
			SYNTAX OCTET STRING
			MAX-ACCESS read-only
			STATUS current
			DESCRIPTION
				"Description."
			::= { gOnuStaInfoEntry 10 }

		
--  1.3.6.1.4.1.37950.1.1.6.1.1.1.1.11
		-- 1.3.6.1.4.1.37950.1.1.6.1.1.1.1.11
		gOnuStaInfoAliveTime OBJECT-TYPE
			SYNTAX OCTET STRING
			MAX-ACCESS read-only
			STATUS current
			DESCRIPTION
				"Description."
			::= { gOnuStaInfoEntry 11 }

		
--  1.3.6.1.4.1.37950.1.1.6.1.1.2
		-- 1.3.6.1.4.1.37950.1.1.6.1.1.2
		gOnuAuthInfoTable OBJECT-TYPE
			SYNTAX SEQUENCE OF GOnuAuthInfoEntry
			MAX-ACCESS not-accessible
			STATUS current
			DESCRIPTION
				"Description."
			::= { gOnuAuthList 2 }

		
--  1.3.6.1.4.1.37950.1.1.6.1.1.2.1
		-- 1.3.6.1.4.1.37950.1.1.6.1.1.2.1
		gOnuAuthInfoEntry OBJECT-TYPE
			SYNTAX GOnuAuthInfoEntry
			MAX-ACCESS not-accessible
			STATUS current
			DESCRIPTION
				"Description."
			INDEX { gOnuAuthInfoPonInx, gOnuAuthInfoOnuInx }
			::= { gOnuAuthInfoTable 1 }

		
		GOnuAuthInfoEntry ::=
			SEQUENCE { 
				gOnuAuthInfoPonInx
					INTEGER,
				gOnuAuthInfoOnuInx
					INTEGER,
				gOnuAuthInfoOnuPName
					OCTET STRING,
				gOnuAuthInfoAuthMode
					INTEGER,
				gOnuAuthInfoAuthInfo
					OCTET STRING,
				gOnuModel
					OCTET STRING
			 }

--  1.3.6.1.4.1.37950.1.1.6.1.1.2.1.1
		-- 1.3.6.1.4.1.37950.1.1.6.1.1.2.1.1
		gOnuAuthInfoPonInx OBJECT-TYPE
			SYNTAX INTEGER (1..16)
			MAX-ACCESS read-only
			STATUS current
			DESCRIPTION
				"Description."
			::= { gOnuAuthInfoEntry 1 }

		
--  1.3.6.1.4.1.37950.1.1.6.1.1.2.1.2
		-- 1.3.6.1.4.1.37950.1.1.6.1.1.2.1.2
		gOnuAuthInfoOnuInx OBJECT-TYPE
			SYNTAX INTEGER (1..128)
			MAX-ACCESS read-only
			STATUS current
			DESCRIPTION
				"Description."
			::= { gOnuAuthInfoEntry 2 }

		
--  1.3.6.1.4.1.37950.1.1.6.1.1.2.1.3
		-- 1.3.6.1.4.1.37950.1.1.6.1.1.2.1.3
		gOnuAuthInfoOnuPName OBJECT-TYPE
			SYNTAX OCTET STRING
			MAX-ACCESS read-only
			STATUS current
			DESCRIPTION
				"Description."
			::= { gOnuAuthInfoEntry 3 }

		
--  1.3.6.1.4.1.37950.1.1.6.1.1.2.1.4
		-- 1.3.6.1.4.1.37950.1.1.6.1.1.2.1.4
		gOnuAuthInfoAuthMode OBJECT-TYPE
			SYNTAX INTEGER
				{
				sn(1),
				pw(2),
				hpw(3),
				snPpw(4),
				snPhpw(5),
				loid(6),
				loidPpw(7),
				loidPhpw(10)
				}
			MAX-ACCESS read-only
			STATUS current
			DESCRIPTION
				"Description."
			::= { gOnuAuthInfoEntry 4 }

		
--  1.3.6.1.4.1.37950.1.1.6.1.1.2.1.5
		-- 1.3.6.1.4.1.37950.1.1.6.1.1.2.1.5
		gOnuAuthInfoAuthInfo OBJECT-TYPE
			SYNTAX OCTET STRING
			MAX-ACCESS read-only
			STATUS current
			DESCRIPTION
				"Description."
			::= { gOnuAuthInfoEntry 5 }

		
--  1.3.6.1.4.1.37950.1.1.6.1.1.2.1.6
		-- 1.3.6.1.4.1.37950.1.1.6.1.1.2.1.6
		gOnuModel OBJECT-TYPE
			SYNTAX OCTET STRING
			MAX-ACCESS read-write
			STATUS current
			DESCRIPTION
				"Description."
			::= { gOnuAuthInfoEntry 6 }

		
--   1.3.6.1.4.1.37950.1.1.5.12.2.1.8
-- 1.3.6.1.4.1.37950.1.1.6.1.1.3
		-- 1.3.6.1.4.1.37950.1.1.6.1.1.3
		gOnuOpticalInfoTable OBJECT-TYPE
			SYNTAX SEQUENCE OF GOnuOpticalInfoEntry
			MAX-ACCESS not-accessible
			STATUS current
			DESCRIPTION
				"Description."
			::= { gOnuAuthList 3 }

		
--   1.3.6.1.4.1.37950.1.1.5.12.2.1.8.1
-- 1.3.6.1.4.1.37950.1.1.6.1.1.3.1
		-- 1.3.6.1.4.1.37950.1.1.6.1.1.3.1
		gOnuOpticalInfoEntry OBJECT-TYPE
			SYNTAX GOnuOpticalInfoEntry
			MAX-ACCESS not-accessible
			STATUS current
			DESCRIPTION
				"Description."
			INDEX { gOnuOpticalInfoPonInx, gOnuOpticalInfoOnuInx }
			::= { gOnuOpticalInfoTable 1 }

		
		GOnuOpticalInfoEntry ::=
			SEQUENCE { 
				gOnuOpticalInfoPonInx
					INTEGER,
				gOnuOpticalInfoOnuInx
					INTEGER,
				gOnuOpticalInfoTemp
					OCTET STRING,
				gOnuOpticalInfoVolt
					OCTET STRING,
				gOnuOpticalInfoBias
					OCTET STRING,
				gOnuOpticalInfoTxPwr
					OCTET STRING,
				gOnuOpticalInfoRxPwr
					OCTET STRING,
				gOnuOpticalInfoRxOptLevOlt
					OCTET STRING
			 }

--   1.3.6.1.4.1.37950.1.1.5.12.2.1.8.1.1
-- 1.3.6.1.4.1.37950.1.1.6.1.1.3.1.1
		-- 1.3.6.1.4.1.37950.1.1.6.1.1.3.1.1
		gOnuOpticalInfoPonInx OBJECT-TYPE
			SYNTAX INTEGER (1..16)
			MAX-ACCESS read-only
			STATUS current
			DESCRIPTION
				"Description."
			::= { gOnuOpticalInfoEntry 1 }

		
--   1.3.6.1.4.1.37950.1.1.5.12.2.1.8.1.2
-- 1.3.6.1.4.1.37950.1.1.6.1.1.3.1.2
		-- 1.3.6.1.4.1.37950.1.1.6.1.1.3.1.2
		gOnuOpticalInfoOnuInx OBJECT-TYPE
			SYNTAX INTEGER (1..128)
			MAX-ACCESS read-only
			STATUS current
			DESCRIPTION
				"Description."
			::= { gOnuOpticalInfoEntry 2 }

		
--   1.3.6.1.4.1.37950.1.1.5.12.2.1.8.1.3
-- 1.3.6.1.4.1.37950.1.1.6.1.1.3.1.3
		-- 1.3.6.1.4.1.37950.1.1.6.1.1.3.1.3
		gOnuOpticalInfoTemp OBJECT-TYPE
			SYNTAX OCTET STRING
			MAX-ACCESS read-only
			STATUS current
			DESCRIPTION
				"Description."
			::= { gOnuOpticalInfoEntry 3 }

		
--   1.3.6.1.4.1.37950.1.1.5.12.2.1.8.1.4
-- 1.3.6.1.4.1.37950.1.1.6.1.1.3.1.4
		-- 1.3.6.1.4.1.37950.1.1.6.1.1.3.1.4
		gOnuOpticalInfoVolt OBJECT-TYPE
			SYNTAX OCTET STRING
			MAX-ACCESS read-only
			STATUS current
			DESCRIPTION
				"Description."
			::= { gOnuOpticalInfoEntry 4 }

		
--   1.3.6.1.4.1.37950.1.1.5.12.2.1.8.1.5
-- 1.3.6.1.4.1.37950.1.1.6.1.1.3.1.5
		-- 1.3.6.1.4.1.37950.1.1.6.1.1.3.1.5
		gOnuOpticalInfoBias OBJECT-TYPE
			SYNTAX OCTET STRING
			MAX-ACCESS read-only
			STATUS current
			DESCRIPTION
				"Description."
			::= { gOnuOpticalInfoEntry 5 }

		
--   1.3.6.1.4.1.37950.1.1.5.12.2.1.8.1.6
-- 1.3.6.1.4.1.37950.1.1.6.1.1.3.1.6
		-- 1.3.6.1.4.1.37950.1.1.6.1.1.3.1.6
		gOnuOpticalInfoTxPwr OBJECT-TYPE
			SYNTAX OCTET STRING
			MAX-ACCESS read-only
			STATUS current
			DESCRIPTION
				"Description."
			::= { gOnuOpticalInfoEntry 6 }

		
--   1.3.6.1.4.1.37950.1.1.5.12.2.1.8.1.7
-- 1.3.6.1.4.1.37950.1.1.6.1.1.3.1.7
		-- 1.3.6.1.4.1.37950.1.1.6.1.1.3.1.7
		gOnuOpticalInfoRxPwr OBJECT-TYPE
			SYNTAX OCTET STRING
			MAX-ACCESS read-only
			STATUS current
			DESCRIPTION
				"Description."
			::= { gOnuOpticalInfoEntry 7 }

		
--  1.3.6.1.4.1.37950.1.1.6.1.1.3.1.8
		-- 1.3.6.1.4.1.37950.1.1.6.1.1.3.1.8
		gOnuOpticalInfoRxOptLevOlt OBJECT-TYPE
			SYNTAX OCTET STRING
			MAX-ACCESS read-only
			STATUS current
			DESCRIPTION
				"Description."
			::= { gOnuOpticalInfoEntry 8 }

		
--  1.3.6.1.4.1.37950.1.1.6.1.1.4
		-- 1.3.6.1.4.1.37950.1.1.6.1.1.4
		gOnuDetailInfoTable OBJECT-TYPE
			SYNTAX SEQUENCE OF GOnuDetailInfoEntry
			MAX-ACCESS not-accessible
			STATUS current
			DESCRIPTION
				"Description."
			::= { gOnuAuthList 4 }

		
--  1.3.6.1.4.1.37950.1.1.6.1.1.4.1
		-- 1.3.6.1.4.1.37950.1.1.6.1.1.4.1
		gOnuDetailInfoEntry OBJECT-TYPE
			SYNTAX GOnuDetailInfoEntry
			MAX-ACCESS not-accessible
			STATUS current
			DESCRIPTION
				"Description."
			INDEX { gOnuDetailInfoPonInx, gOnuDetailInfoOnuInx }
			::= { gOnuDetailInfoTable 1 }

		
		GOnuDetailInfoEntry ::=
			SEQUENCE { 
				gOnuDetailInfoPonInx
					INTEGER,
				gOnuDetailInfoOnuInx
					INTEGER,
				gOnuDetailInfoVendorId
					OCTET STRING,
				gOnuDetailInfoVersion
					OCTET STRING,
				gOnuDetailInfoSn
					OCTET STRING,
				gOnuDetailInfoAdminSta
					Integer32,
				gOnuDetailInfoBatMonitor
					Integer32,
				gOnuDetailInfoSecMode
					Integer32,
				gOnuDetailInfoProductCode
					Integer32,
				gOnuDetailInfoTotalPriQ
					Integer32,
				gOnuDetailInfoTotalTraQ
					Integer32,
				gOnuDetailInfoTraMngOpt
					Integer32,
				gOnuDetailInfoOpSta
					Integer32,
				gOnuDetailInfoEquipmentId
					OCTET STRING,
				gOnuDetailInfoOmccVer
					Integer32,
				gOnuDetailInfoSecCap
					Integer32,
				gOnuDetailInfoModel
					OCTET STRING,
				gOnuDetailInfoSurTime
					OCTET STRING,
				gOnuDetailInfoTotalGem
					OCTET STRING,
				gOnuDetailInfoSysUpTime
					OCTET STRING,
				gOnuDetailInfoRegionCode
					OCTET STRING,
				gOnuDetailInfoProductSn
					OCTET STRING,
				gOnuDetailInfoChipInfo
					Integer32,
				gOnuDetailInfoOnuDesc
					OCTET STRING,
				gOnuDetailInfoMainVer
					OCTET STRING,
				gOnuDetailInfoStandbyVer
					OCTET STRING,
				gOnuDetailInfoStartupTime
					OCTET STRING
			 }

--  1.3.6.1.4.1.37950.1.1.6.1.1.4.1.1
		-- 1.3.6.1.4.1.37950.1.1.6.1.1.4.1.1
		gOnuDetailInfoPonInx OBJECT-TYPE
			SYNTAX INTEGER (1..16)
			MAX-ACCESS read-only
			STATUS current
			DESCRIPTION
				"Description."
			::= { gOnuDetailInfoEntry 1 }

		
--  1.3.6.1.4.1.37950.1.1.6.1.1.4.1.2
		-- 1.3.6.1.4.1.37950.1.1.6.1.1.4.1.2
		gOnuDetailInfoOnuInx OBJECT-TYPE
			SYNTAX INTEGER (1..128)
			MAX-ACCESS read-only
			STATUS current
			DESCRIPTION
				"Description."
			::= { gOnuDetailInfoEntry 2 }

		
--  1.3.6.1.4.1.37950.1.1.6.1.1.4.1.3
		-- 1.3.6.1.4.1.37950.1.1.6.1.1.4.1.3
		gOnuDetailInfoVendorId OBJECT-TYPE
			SYNTAX OCTET STRING
			MAX-ACCESS read-only
			STATUS current
			DESCRIPTION
				"Description."
			::= { gOnuDetailInfoEntry 3 }

		
--  1.3.6.1.4.1.37950.1.1.6.1.1.4.1.4
		-- 1.3.6.1.4.1.37950.1.1.6.1.1.4.1.4
		gOnuDetailInfoVersion OBJECT-TYPE
			SYNTAX OCTET STRING
			MAX-ACCESS read-only
			STATUS current
			DESCRIPTION
				"Description."
			::= { gOnuDetailInfoEntry 4 }

		
--  1.3.6.1.4.1.37950.1.1.6.1.1.4.1.5
		-- 1.3.6.1.4.1.37950.1.1.6.1.1.4.1.5
		gOnuDetailInfoSn OBJECT-TYPE
			SYNTAX OCTET STRING
			MAX-ACCESS read-only
			STATUS current
			DESCRIPTION
				"Description."
			::= { gOnuDetailInfoEntry 5 }

		
--  1.3.6.1.4.1.37950.1.1.6.1.1.4.1.6
		-- 1.3.6.1.4.1.37950.1.1.6.1.1.4.1.6
		gOnuDetailInfoAdminSta OBJECT-TYPE
			SYNTAX Integer32
			MAX-ACCESS read-only
			STATUS current
			DESCRIPTION
				"Description."
			::= { gOnuDetailInfoEntry 6 }

		
--  1.3.6.1.4.1.37950.1.1.6.1.1.4.1.7
		-- 1.3.6.1.4.1.37950.1.1.6.1.1.4.1.7
		gOnuDetailInfoBatMonitor OBJECT-TYPE
			SYNTAX Integer32
			MAX-ACCESS read-only
			STATUS current
			DESCRIPTION
				"Description."
			::= { gOnuDetailInfoEntry 7 }

		
--  1.3.6.1.4.1.37950.1.1.6.1.1.4.1.8
		-- 1.3.6.1.4.1.37950.1.1.6.1.1.4.1.8
		gOnuDetailInfoSecMode OBJECT-TYPE
			SYNTAX Integer32
			MAX-ACCESS read-only
			STATUS current
			DESCRIPTION
				"Description."
			::= { gOnuDetailInfoEntry 8 }

		
--  1.3.6.1.4.1.37950.1.1.6.1.1.4.1.9
		-- 1.3.6.1.4.1.37950.1.1.6.1.1.4.1.9
		gOnuDetailInfoProductCode OBJECT-TYPE
			SYNTAX Integer32
			MAX-ACCESS read-only
			STATUS current
			DESCRIPTION
				"Description."
			::= { gOnuDetailInfoEntry 9 }

		
--  1.3.6.1.4.1.37950.1.1.6.1.1.4.1.10
		-- 1.3.6.1.4.1.37950.1.1.6.1.1.4.1.10
		gOnuDetailInfoTotalPriQ OBJECT-TYPE
			SYNTAX Integer32
			MAX-ACCESS read-only
			STATUS current
			DESCRIPTION
				"Description."
			::= { gOnuDetailInfoEntry 10 }

		
--  1.3.6.1.4.1.37950.1.1.6.1.1.4.1.11
		-- 1.3.6.1.4.1.37950.1.1.6.1.1.4.1.11
		gOnuDetailInfoTotalTraQ OBJECT-TYPE
			SYNTAX Integer32
			MAX-ACCESS read-only
			STATUS current
			DESCRIPTION
				"Description."
			::= { gOnuDetailInfoEntry 11 }

		
--  1.3.6.1.4.1.37950.1.1.6.1.1.4.1.12
		-- 1.3.6.1.4.1.37950.1.1.6.1.1.4.1.12
		gOnuDetailInfoTraMngOpt OBJECT-TYPE
			SYNTAX Integer32
			MAX-ACCESS read-only
			STATUS current
			DESCRIPTION
				"Description."
			::= { gOnuDetailInfoEntry 12 }

		
--  1.3.6.1.4.1.37950.1.1.6.1.1.4.1.13
		-- 1.3.6.1.4.1.37950.1.1.6.1.1.4.1.13
		gOnuDetailInfoOpSta OBJECT-TYPE
			SYNTAX Integer32
			MAX-ACCESS read-only
			STATUS current
			DESCRIPTION
				"Description."
			::= { gOnuDetailInfoEntry 13 }

		
--  1.3.6.1.4.1.37950.1.1.6.1.1.4.1.14
		-- 1.3.6.1.4.1.37950.1.1.6.1.1.4.1.14
		gOnuDetailInfoEquipmentId OBJECT-TYPE
			SYNTAX OCTET STRING
			MAX-ACCESS read-only
			STATUS current
			DESCRIPTION
				"Description."
			::= { gOnuDetailInfoEntry 14 }

		
--  1.3.6.1.4.1.37950.1.1.6.1.1.4.1.15
		-- 1.3.6.1.4.1.37950.1.1.6.1.1.4.1.15
		gOnuDetailInfoOmccVer OBJECT-TYPE
			SYNTAX Integer32
			MAX-ACCESS read-only
			STATUS current
			DESCRIPTION
				"Description."
			::= { gOnuDetailInfoEntry 15 }

		
--  1.3.6.1.4.1.37950.1.1.6.1.1.4.1.16
		-- 1.3.6.1.4.1.37950.1.1.6.1.1.4.1.16
		gOnuDetailInfoSecCap OBJECT-TYPE
			SYNTAX Integer32
			MAX-ACCESS read-only
			STATUS current
			DESCRIPTION
				"Description."
			::= { gOnuDetailInfoEntry 16 }

		
--  1.3.6.1.4.1.37950.1.1.6.1.1.4.1.17
		-- 1.3.6.1.4.1.37950.1.1.6.1.1.4.1.17
		gOnuDetailInfoModel OBJECT-TYPE
			SYNTAX OCTET STRING
			MAX-ACCESS read-only
			STATUS current
			DESCRIPTION
				"Description."
			::= { gOnuDetailInfoEntry 17 }

		
--  1.3.6.1.4.1.37950.1.1.6.1.1.4.1.18
		-- 1.3.6.1.4.1.37950.1.1.6.1.1.4.1.18
		gOnuDetailInfoSurTime OBJECT-TYPE
			SYNTAX OCTET STRING
			MAX-ACCESS read-only
			STATUS current
			DESCRIPTION
				"Description."
			::= { gOnuDetailInfoEntry 18 }

		
--  1.3.6.1.4.1.37950.1.1.6.1.1.4.1.19
		-- 1.3.6.1.4.1.37950.1.1.6.1.1.4.1.19
		gOnuDetailInfoTotalGem OBJECT-TYPE
			SYNTAX OCTET STRING
			MAX-ACCESS read-only
			STATUS current
			DESCRIPTION
				"Description."
			::= { gOnuDetailInfoEntry 19 }

		
--  1.3.6.1.4.1.37950.1.1.6.1.1.4.1.20
		-- 1.3.6.1.4.1.37950.1.1.6.1.1.4.1.20
		gOnuDetailInfoSysUpTime OBJECT-TYPE
			SYNTAX OCTET STRING
			MAX-ACCESS read-only
			STATUS current
			DESCRIPTION
				"Description."
			::= { gOnuDetailInfoEntry 20 }

		
--  1.3.6.1.4.1.37950.1.1.6.1.1.4.1.21
		-- 1.3.6.1.4.1.37950.1.1.6.1.1.4.1.21
		gOnuDetailInfoRegionCode OBJECT-TYPE
			SYNTAX OCTET STRING
			MAX-ACCESS read-only
			STATUS current
			DESCRIPTION
				"Description."
			::= { gOnuDetailInfoEntry 21 }

		
--  1.3.6.1.4.1.37950.1.1.6.1.1.4.1.22
		-- 1.3.6.1.4.1.37950.1.1.6.1.1.4.1.22
		gOnuDetailInfoProductSn OBJECT-TYPE
			SYNTAX OCTET STRING
			MAX-ACCESS read-only
			STATUS current
			DESCRIPTION
				"Description."
			::= { gOnuDetailInfoEntry 22 }

		
--  1.3.6.1.4.1.37950.1.1.6.1.1.4.1.23
		-- 1.3.6.1.4.1.37950.1.1.6.1.1.4.1.23
		gOnuDetailInfoChipInfo OBJECT-TYPE
			SYNTAX Integer32
			MAX-ACCESS read-only
			STATUS current
			DESCRIPTION
				"Description."
			::= { gOnuDetailInfoEntry 23 }

		
--  1.3.6.1.4.1.37950.1.1.6.1.1.4.1.24
		-- 1.3.6.1.4.1.37950.1.1.6.1.1.4.1.24
		gOnuDetailInfoOnuDesc OBJECT-TYPE
			SYNTAX OCTET STRING
			MAX-ACCESS read-write
			STATUS current
			DESCRIPTION
				"Description."
			::= { gOnuDetailInfoEntry 24 }

		
--  1.3.6.1.4.1.37950.1.1.6.1.1.4.1.25
		-- 1.3.6.1.4.1.37950.1.1.6.1.1.4.1.25
		gOnuDetailInfoMainVer OBJECT-TYPE
			SYNTAX OCTET STRING
			MAX-ACCESS read-only
			STATUS current
			DESCRIPTION
				"Description."
			::= { gOnuDetailInfoEntry 25 }

		
--  1.3.6.1.4.1.37950.1.1.6.1.1.4.1.26
		-- 1.3.6.1.4.1.37950.1.1.6.1.1.4.1.26
		gOnuDetailInfoStandbyVer OBJECT-TYPE
			SYNTAX OCTET STRING
			MAX-ACCESS read-only
			STATUS current
			DESCRIPTION
				"Description."
			::= { gOnuDetailInfoEntry 26 }

		
		-- 1.3.6.1.4.1.37950.1.1.6.1.1.4.1.27
		gOnuDetailInfoStartupTime OBJECT-TYPE
			SYNTAX OCTET STRING
			MAX-ACCESS read-write
			STATUS current
			DESCRIPTION
				"Description."
			::= { gOnuDetailInfoEntry 27 }

		
--  1.3.6.1.4.1.37950.1.1.6.1.1.5
		-- 1.3.6.1.4.1.37950.1.1.6.1.1.5
		gOnuOp OBJECT IDENTIFIER ::= { gOnuAuthList 5 }

		
--  1.3.6.1.4.1.37950.1.1.6.1.1.5.1
		-- 1.3.6.1.4.1.37950.1.1.6.1.1.5.1
		gOnuOpPonInx OBJECT-TYPE
			SYNTAX Integer32 (1..16)
			MAX-ACCESS read-write
			STATUS current
			DESCRIPTION
				"Description."
			::= { gOnuOp 1 }

		
--  1.3.6.1.4.1.37950.1.1.6.1.1.5.2
		-- 1.3.6.1.4.1.37950.1.1.6.1.1.5.2
		gOnuOpOnuInx OBJECT-TYPE
			SYNTAX Integer32 (1..128)
			MAX-ACCESS read-write
			STATUS current
			DESCRIPTION
				"Description."
			::= { gOnuOp 2 }

		
--  1.3.6.1.4.1.37950.1.1.6.1.1.5.3
		-- 1.3.6.1.4.1.37950.1.1.6.1.1.5.3
		gOnuOpAction OBJECT-TYPE
			SYNTAX INTEGER
				{
				reboot(1),
				del(2),
				activate(3),
				deactivate(4),
				del_offline(5),
				del_all(6)
				}
			MAX-ACCESS read-write
			STATUS current
			DESCRIPTION
				"Description."
			::= { gOnuOp 3 }

		
--  1.3.6.1.4.1.37950.1.1.6.1.1.6
		-- 1.3.6.1.4.1.37950.1.1.6.1.1.6
		gOnuManualAdd OBJECT IDENTIFIER ::= { gOnuAuthList 6 }

		
--  1.3.6.1.4.1.37950.1.1.6.1.1.6.1
		-- 1.3.6.1.4.1.37950.1.1.6.1.1.6.1
		gOnuAddPonInx OBJECT-TYPE
			SYNTAX Integer32 (1..16)
			MAX-ACCESS read-write
			STATUS current
			DESCRIPTION
				"Description."
			::= { gOnuManualAdd 1 }

		
--  1.3.6.1.4.1.37950.1.1.6.1.1.6.2
		-- 1.3.6.1.4.1.37950.1.1.6.1.1.6.2
		gOnuAddOnuInx OBJECT-TYPE
			SYNTAX Integer32 (1..128)
			MAX-ACCESS read-write
			STATUS current
			DESCRIPTION
				"Description."
			::= { gOnuManualAdd 2 }

		
--  1.3.6.1.4.1.37950.1.1.6.1.1.6.3
		-- 1.3.6.1.4.1.37950.1.1.6.1.1.6.3
		gOnuAddAuthMode OBJECT-TYPE
			SYNTAX Integer32 (1..10)
			MAX-ACCESS read-write
			STATUS current
			DESCRIPTION
				"Description."
			::= { gOnuManualAdd 3 }

		
--  1.3.6.1.4.1.37950.1.1.6.1.1.6.4
		-- 1.3.6.1.4.1.37950.1.1.6.1.1.6.4
		gOnuAddOnuProfile OBJECT-TYPE
			SYNTAX OCTET STRING
			MAX-ACCESS read-write
			STATUS current
			DESCRIPTION
				"Description."
			::= { gOnuManualAdd 4 }

		
--  1.3.6.1.4.1.37950.1.1.6.1.1.6.5
		-- 1.3.6.1.4.1.37950.1.1.6.1.1.6.5
		gOnuAddSn OBJECT-TYPE
			SYNTAX OCTET STRING
			MAX-ACCESS read-write
			STATUS current
			DESCRIPTION
				"Description."
			::= { gOnuManualAdd 5 }

		
--  1.3.6.1.4.1.37950.1.1.6.1.1.6.6
		-- 1.3.6.1.4.1.37950.1.1.6.1.1.6.6
		gOnuAddLoid OBJECT-TYPE
			SYNTAX OCTET STRING
			MAX-ACCESS read-write
			STATUS current
			DESCRIPTION
				"Description."
			::= { gOnuManualAdd 6 }

		
--  1.3.6.1.4.1.37950.1.1.6.1.1.6.7
		-- 1.3.6.1.4.1.37950.1.1.6.1.1.6.7
		gOnuAddPw OBJECT-TYPE
			SYNTAX OCTET STRING
			MAX-ACCESS read-write
			STATUS current
			DESCRIPTION
				"Description."
			::= { gOnuManualAdd 7 }

		
--  1.3.6.1.4.1.37950.1.1.6.1.1.6.8
		-- 1.3.6.1.4.1.37950.1.1.6.1.1.6.8
		gOnuAddAction OBJECT-TYPE
			SYNTAX INTEGER { add(1) }
			MAX-ACCESS read-write
			STATUS current
			DESCRIPTION
				"Description."
			::= { gOnuManualAdd 8 }

		
--  1.3.6.1.4.1.37950.1.1.6.1.1.7
		-- 1.3.6.1.4.1.37950.1.1.6.1.1.7
		gOnuCfg OBJECT IDENTIFIER ::= { gOnuAuthList 7 }

		
--  1.3.6.1.4.1.37950.1.1.6.1.1.7.1
		-- 1.3.6.1.4.1.37950.1.1.6.1.1.7.1
		gOnuCfgTcont OBJECT IDENTIFIER ::= { gOnuCfg 1 }

		
--  1.3.6.1.4.1.37950.1.1.6.1.1.7.1.1
		-- 1.3.6.1.4.1.37950.1.1.6.1.1.7.1.1
		gOnuCfgTcontPonInx OBJECT-TYPE
			SYNTAX Integer32 (1..16)
			MAX-ACCESS read-write
			STATUS current
			DESCRIPTION
				"Description."
			::= { gOnuCfgTcont 1 }

		
--  1.3.6.1.4.1.37950.1.1.6.1.1.7.1.2
		-- 1.3.6.1.4.1.37950.1.1.6.1.1.7.1.2
		gOnuCfgTcontOnuInx OBJECT-TYPE
			SYNTAX Integer32 (1..128)
			MAX-ACCESS read-write
			STATUS current
			DESCRIPTION
				"Description."
			::= { gOnuCfgTcont 2 }

		
--  1.3.6.1.4.1.37950.1.1.6.1.1.7.1.3
		-- 1.3.6.1.4.1.37950.1.1.6.1.1.7.1.3
		gOnuCfgTcontId OBJECT-TYPE
			SYNTAX Integer32 (1..255)
			MAX-ACCESS read-write
			STATUS current
			DESCRIPTION
				"Description."
			::= { gOnuCfgTcont 3 }

		
--  1.3.6.1.4.1.37950.1.1.6.1.1.7.1.4
		-- 1.3.6.1.4.1.37950.1.1.6.1.1.7.1.4
		gOnuCfgTcontName OBJECT-TYPE
			SYNTAX OCTET STRING
			MAX-ACCESS read-write
			STATUS current
			DESCRIPTION
				"Description."
			::= { gOnuCfgTcont 4 }

		
--  1.3.6.1.4.1.37950.1.1.6.1.1.7.1.5
		-- 1.3.6.1.4.1.37950.1.1.6.1.1.7.1.5
		gOnuCfgTcontDba OBJECT-TYPE
			SYNTAX OCTET STRING
			MAX-ACCESS read-write
			STATUS current
			DESCRIPTION
				"Description."
			::= { gOnuCfgTcont 5 }

		
--  1.3.6.1.4.1.37950.1.1.6.1.1.7.1.6
		-- 1.3.6.1.4.1.37950.1.1.6.1.1.7.1.6
		gOnuCfgTcontAction OBJECT-TYPE
			SYNTAX INTEGER
				{
				add(1),
				del(2),
				modify(3)
				}
			MAX-ACCESS read-write
			STATUS current
			DESCRIPTION
				"Description."
			::= { gOnuCfgTcont 6 }

		
--  1.3.6.1.4.1.37950.1.1.6.1.1.7.2
		-- 1.3.6.1.4.1.37950.1.1.6.1.1.7.2
		gOnuCfgGem OBJECT IDENTIFIER ::= { gOnuCfg 2 }

		
--  1.3.6.1.4.1.37950.1.1.6.1.1.7.2.1
		-- 1.3.6.1.4.1.37950.1.1.6.1.1.7.2.1
		gOnuCfgGemPonInx OBJECT-TYPE
			SYNTAX Integer32 (1..16)
			MAX-ACCESS read-write
			STATUS current
			DESCRIPTION
				"Description."
			::= { gOnuCfgGem 1 }

		
--  1.3.6.1.4.1.37950.1.1.6.1.1.7.2.2
		-- 1.3.6.1.4.1.37950.1.1.6.1.1.7.2.2
		gOnuCfgGemOnuInx OBJECT-TYPE
			SYNTAX Integer32 (1..128)
			MAX-ACCESS read-write
			STATUS current
			DESCRIPTION
				"Description."
			::= { gOnuCfgGem 2 }

		
--  1.3.6.1.4.1.37950.1.1.6.1.1.7.2.3
		-- 1.3.6.1.4.1.37950.1.1.6.1.1.7.2.3
		gOnuCfgGemId OBJECT-TYPE
			SYNTAX Integer32 (1..255)
			MAX-ACCESS read-write
			STATUS current
			DESCRIPTION
				"Description."
			::= { gOnuCfgGem 3 }

		
--  1.3.6.1.4.1.37950.1.1.6.1.1.7.2.4
		-- 1.3.6.1.4.1.37950.1.1.6.1.1.7.2.4
		gOnuCfgGemTcont OBJECT-TYPE
			SYNTAX Integer32 (1..255)
			MAX-ACCESS read-write
			STATUS current
			DESCRIPTION
				"Description."
			::= { gOnuCfgGem 4 }

		
--  1.3.6.1.4.1.37950.1.1.6.1.1.7.2.5
		-- 1.3.6.1.4.1.37950.1.1.6.1.1.7.2.5
		gOnuCfgGemName OBJECT-TYPE
			SYNTAX OCTET STRING
			MAX-ACCESS read-write
			STATUS current
			DESCRIPTION
				"Description."
			::= { gOnuCfgGem 5 }

		
--  1.3.6.1.4.1.37950.1.1.6.1.1.7.2.6
		-- 1.3.6.1.4.1.37950.1.1.6.1.1.7.2.6
		gOnuCfgGemCos OBJECT-TYPE
			SYNTAX Integer32 (0..8)
			MAX-ACCESS read-write
			STATUS current
			DESCRIPTION
				"Description."
			::= { gOnuCfgGem 6 }

		
--  1.3.6.1.4.1.37950.1.1.6.1.1.7.2.7
		-- 1.3.6.1.4.1.37950.1.1.6.1.1.7.2.7
		gOnuCfgGemUpTra OBJECT-TYPE
			SYNTAX OCTET STRING
			MAX-ACCESS read-write
			STATUS current
			DESCRIPTION
				"Description."
			::= { gOnuCfgGem 7 }

		
--  1.3.6.1.4.1.37950.1.1.6.1.1.7.2.8
		-- 1.3.6.1.4.1.37950.1.1.6.1.1.7.2.8
		gOnuCfgGemDnTra OBJECT-TYPE
			SYNTAX OCTET STRING
			MAX-ACCESS read-write
			STATUS current
			DESCRIPTION
				"Description."
			::= { gOnuCfgGem 8 }

		
--  1.3.6.1.4.1.37950.1.1.6.1.1.7.2.9
		-- 1.3.6.1.4.1.37950.1.1.6.1.1.7.2.9
		gOnuCfgGemUpQueId OBJECT-TYPE
			SYNTAX Integer32 (0..4)
			MAX-ACCESS read-write
			STATUS current
			DESCRIPTION
				"Description."
			::= { gOnuCfgGem 9 }

		
--  1.3.6.1.4.1.37950.1.1.6.1.1.7.2.10
		-- 1.3.6.1.4.1.37950.1.1.6.1.1.7.2.10
		gOnuCfgGemDnQueId OBJECT-TYPE
			SYNTAX Integer32 (0..8)
			MAX-ACCESS read-write
			STATUS current
			DESCRIPTION
				"Description."
			::= { gOnuCfgGem 10 }

		
--  1.3.6.1.4.1.37950.1.1.6.1.1.7.2.11
		-- 1.3.6.1.4.1.37950.1.1.6.1.1.7.2.11
		gOnuCfgGemSta OBJECT-TYPE
			SYNTAX Integer32 (0..1)
			MAX-ACCESS read-write
			STATUS current
			DESCRIPTION
				"Description."
			::= { gOnuCfgGem 11 }

		
--  1.3.6.1.4.1.37950.1.1.6.1.1.7.2.12
		-- 1.3.6.1.4.1.37950.1.1.6.1.1.7.2.12
		gOnuCfgGemAction OBJECT-TYPE
			SYNTAX INTEGER
				{
				add(1),
				del(2),
				modify(3)
				}
			MAX-ACCESS read-write
			STATUS current
			DESCRIPTION
				"Description."
			::= { gOnuCfgGem 12 }

		
--  1.3.6.1.4.1.37950.1.1.6.1.1.7.3
		-- 1.3.6.1.4.1.37950.1.1.6.1.1.7.3
		gOnuCfgSrv OBJECT IDENTIFIER ::= { gOnuCfg 3 }

		
--  1.3.6.1.4.1.37950.1.1.6.1.1.7.3.1
		-- 1.3.6.1.4.1.37950.1.1.6.1.1.7.3.1
		gOnuCfgSrvPonInx OBJECT-TYPE
			SYNTAX Integer32 (1..16)
			MAX-ACCESS read-write
			STATUS current
			DESCRIPTION
				"Description."
			::= { gOnuCfgSrv 1 }

		
--  1.3.6.1.4.1.37950.1.1.6.1.1.7.3.2
		-- 1.3.6.1.4.1.37950.1.1.6.1.1.7.3.2
		gOnuCfgSrvOnuInx OBJECT-TYPE
			SYNTAX Integer32 (1..128)
			MAX-ACCESS read-write
			STATUS current
			DESCRIPTION
				"Description."
			::= { gOnuCfgSrv 2 }

		
--  1.3.6.1.4.1.37950.1.1.6.1.1.7.3.3
		-- 1.3.6.1.4.1.37950.1.1.6.1.1.7.3.3
		gOnuCfgSrvName OBJECT-TYPE
			SYNTAX OCTET STRING
			MAX-ACCESS read-write
			STATUS current
			DESCRIPTION
				"Description."
			::= { gOnuCfgSrv 3 }

		
--  1.3.6.1.4.1.37950.1.1.6.1.1.7.3.4
		-- 1.3.6.1.4.1.37950.1.1.6.1.1.7.3.4
		gOnuCfgSrvMode OBJECT-TYPE
			SYNTAX Integer32 (0..2)
			MAX-ACCESS read-write
			STATUS current
			DESCRIPTION
				"Description."
			::= { gOnuCfgSrv 4 }

		
--  1.3.6.1.4.1.37950.1.1.6.1.1.7.3.5
		-- 1.3.6.1.4.1.37950.1.1.6.1.1.7.3.5
		gOnuCfgSrvGemId OBJECT-TYPE
			SYNTAX Integer32 (1..255)
			MAX-ACCESS read-write
			STATUS current
			DESCRIPTION
				"Description."
			::= { gOnuCfgSrv 5 }

		
--  1.3.6.1.4.1.37950.1.1.6.1.1.7.3.6
		-- 1.3.6.1.4.1.37950.1.1.6.1.1.7.3.6
		gOnuCfgSrvVlanList OBJECT-TYPE
			SYNTAX OCTET STRING
			MAX-ACCESS read-write
			STATUS current
			DESCRIPTION
				"Description."
			::= { gOnuCfgSrv 6 }

		
--  1.3.6.1.4.1.37950.1.1.6.1.1.7.3.7
		-- 1.3.6.1.4.1.37950.1.1.6.1.1.7.3.7
		gOnuCfgSrvCosList OBJECT-TYPE
			SYNTAX OCTET STRING
			MAX-ACCESS read-write
			STATUS current
			DESCRIPTION
				"Description."
			::= { gOnuCfgSrv 7 }

		
--  1.3.6.1.4.1.37950.1.1.6.1.1.7.3.8
		-- 1.3.6.1.4.1.37950.1.1.6.1.1.7.3.8
		gOnuCfgSrvPortType OBJECT-TYPE
			SYNTAX INTEGER
				{
				null(0),
				eth(1),
				iphost(2)
				}
			MAX-ACCESS read-write
			STATUS current
			DESCRIPTION
				"Description."
			::= { gOnuCfgSrv 8 }

		
--  1.3.6.1.4.1.37950.1.1.6.1.1.7.3.9
		-- 1.3.6.1.4.1.37950.1.1.6.1.1.7.3.9
		gOnuCfgSrvPortNum OBJECT-TYPE
			SYNTAX Integer32
			MAX-ACCESS read-write
			STATUS current
			DESCRIPTION
				"Description."
			::= { gOnuCfgSrv 9 }

		
--  1.3.6.1.4.1.37950.1.1.6.1.1.7.3.10
		-- 1.3.6.1.4.1.37950.1.1.6.1.1.7.3.10
		gOnuCfgSrvAction OBJECT-TYPE
			SYNTAX INTEGER
				{
				add(1),
				del(2),
				modify(3)
				}
			MAX-ACCESS read-write
			STATUS current
			DESCRIPTION
				"Description."
			::= { gOnuCfgSrv 10 }

		
--  1.3.6.1.4.1.37950.1.1.6.1.1.7.4
		-- 1.3.6.1.4.1.37950.1.1.6.1.1.7.4
		gOnuCfgSrvPort OBJECT IDENTIFIER ::= { gOnuCfg 4 }

		
--  1.3.6.1.4.1.37950.1.1.6.1.1.7.4.1
		-- 1.3.6.1.4.1.37950.1.1.6.1.1.7.4.1
		gOnuCfgSrvPortPonInx OBJECT-TYPE
			SYNTAX Integer32 (1..16)
			MAX-ACCESS read-write
			STATUS current
			DESCRIPTION
				"Description."
			::= { gOnuCfgSrvPort 1 }

		
--  1.3.6.1.4.1.37950.1.1.6.1.1.7.4.2
		-- 1.3.6.1.4.1.37950.1.1.6.1.1.7.4.2
		gOnuCfgSrvPortOnuInx OBJECT-TYPE
			SYNTAX Integer32 (1..128)
			MAX-ACCESS read-write
			STATUS current
			DESCRIPTION
				"Description."
			::= { gOnuCfgSrvPort 2 }

		
--  1.3.6.1.4.1.37950.1.1.6.1.1.7.4.3
		-- 1.3.6.1.4.1.37950.1.1.6.1.1.7.4.3
		gOnuCfgSrvPortId OBJECT-TYPE
			SYNTAX Integer32 (1..128)
			MAX-ACCESS read-write
			STATUS current
			DESCRIPTION
				"Description."
			::= { gOnuCfgSrvPort 3 }

		
--  1.3.6.1.4.1.37950.1.1.6.1.1.7.4.4
		-- 1.3.6.1.4.1.37950.1.1.6.1.1.7.4.4
		gOnuCfgSrvPortGemId OBJECT-TYPE
			SYNTAX Integer32 (1..255)
			MAX-ACCESS read-write
			STATUS current
			DESCRIPTION
				"Description."
			::= { gOnuCfgSrvPort 4 }

		
--  1.3.6.1.4.1.37950.1.1.6.1.1.7.4.5
		-- 1.3.6.1.4.1.37950.1.1.6.1.1.7.4.5
		gOnuCfgSrvPortSetMode OBJECT-TYPE
			SYNTAX INTEGER
				{
				cvlan(1),
				cvlanEtype(2),
				cvlanUserDefinedEtype(3),
				cvlanPriority(4),
				cvlanRangeTransparent(5),
				untagged(6),
				untaggedEtype(7),
				untaggedUserDefinedEtype(8)
				}
			MAX-ACCESS read-write
			STATUS current
			DESCRIPTION
				"Description."
			::= { gOnuCfgSrvPort 5 }

		
--  1.3.6.1.4.1.37950.1.1.6.1.1.7.4.6
		-- 1.3.6.1.4.1.37950.1.1.6.1.1.7.4.6
		gOnuCfgSrvPortDesc OBJECT-TYPE
			SYNTAX OCTET STRING
			MAX-ACCESS read-write
			STATUS current
			DESCRIPTION
				"Description."
			::= { gOnuCfgSrvPort 6 }

		
--  1.3.6.1.4.1.37950.1.1.6.1.1.7.4.7
		-- 1.3.6.1.4.1.37950.1.1.6.1.1.7.4.7
		gOnuCfgSrvPortUserVlan OBJECT-TYPE
			SYNTAX Integer32 (0..4093)
			MAX-ACCESS read-write
			STATUS current
			DESCRIPTION
				"Description."
			::= { gOnuCfgSrvPort 7 }

		
--  1.3.6.1.4.1.37950.1.1.6.1.1.7.4.8
		-- 1.3.6.1.4.1.37950.1.1.6.1.1.7.4.8
		gOnuCfgSrvPortBVid OBJECT-TYPE
			SYNTAX Integer32 (0..4093)
			MAX-ACCESS read-write
			STATUS current
			DESCRIPTION
				"Description."
			::= { gOnuCfgSrvPort 8 }

		
--  1.3.6.1.4.1.37950.1.1.6.1.1.7.4.9
		-- 1.3.6.1.4.1.37950.1.1.6.1.1.7.4.9
		gOnuCfgSrvPortEVid OBJECT-TYPE
			SYNTAX Integer32 (0..4093)
			MAX-ACCESS read-write
			STATUS current
			DESCRIPTION
				"Description."
			::= { gOnuCfgSrvPort 9 }

		
--  1.3.6.1.4.1.37950.1.1.6.1.1.7.4.10
		-- 1.3.6.1.4.1.37950.1.1.6.1.1.7.4.10
		gOnuCfgSrvPortUPri OBJECT-TYPE
			SYNTAX Integer32 (0..7)
			MAX-ACCESS read-write
			STATUS current
			DESCRIPTION
				"Description."
			::= { gOnuCfgSrvPort 10 }

		
--  1.3.6.1.4.1.37950.1.1.6.1.1.7.4.11
		-- 1.3.6.1.4.1.37950.1.1.6.1.1.7.4.11
		gOnuCfgSrvPortEtype OBJECT-TYPE
			SYNTAX INTEGER
				{
				pppoe(1),
				ipoe(2)
				}
			MAX-ACCESS read-write
			STATUS current
			DESCRIPTION
				"Description."
			::= { gOnuCfgSrvPort 11 }

		
--  1.3.6.1.4.1.37950.1.1.6.1.1.7.4.12
		-- 1.3.6.1.4.1.37950.1.1.6.1.1.7.4.12
		gOnuCfgSrvPortUserEtype OBJECT-TYPE
			SYNTAX OCTET STRING
			MAX-ACCESS read-write
			STATUS current
			DESCRIPTION
				"Description."
			::= { gOnuCfgSrvPort 12 }

		
--  1.3.6.1.4.1.37950.1.1.6.1.1.7.4.13
		-- 1.3.6.1.4.1.37950.1.1.6.1.1.7.4.13
		gOnuCfgSrvPortVid OBJECT-TYPE
			SYNTAX Integer32 (0..4093)
			MAX-ACCESS read-write
			STATUS current
			DESCRIPTION
				"Description."
			::= { gOnuCfgSrvPort 13 }

		
--  1.3.6.1.4.1.37950.1.1.6.1.1.7.4.14
		-- 1.3.6.1.4.1.37950.1.1.6.1.1.7.4.14
		gOnuCfgSrvPortCos OBJECT-TYPE
			SYNTAX Integer32 (-1..7)
			MAX-ACCESS read-write
			STATUS current
			DESCRIPTION
				"Description."
			::= { gOnuCfgSrvPort 14 }

		
--  1.3.6.1.4.1.37950.1.1.6.1.1.7.4.15
		-- 1.3.6.1.4.1.37950.1.1.6.1.1.7.4.15
		gOnuCfgSrvPortSVid OBJECT-TYPE
			SYNTAX Integer32 (0..4093)
			MAX-ACCESS read-write
			STATUS current
			DESCRIPTION
				"Description."
			::= { gOnuCfgSrvPort 15 }

		
--  1.3.6.1.4.1.37950.1.1.6.1.1.7.4.16
		-- 1.3.6.1.4.1.37950.1.1.6.1.1.7.4.16
		gOnuCfgSrvPortSCos OBJECT-TYPE
			SYNTAX Integer32 (-1..7)
			MAX-ACCESS read-write
			STATUS current
			DESCRIPTION
				"Description."
			::= { gOnuCfgSrvPort 16 }

		
--  1.3.6.1.4.1.37950.1.1.6.1.1.7.4.17
		-- 1.3.6.1.4.1.37950.1.1.6.1.1.7.4.17
		gOnuCfgSrvPortAction OBJECT-TYPE
			SYNTAX INTEGER
				{
				add(1),
				del(2),
				modify(3)
				}
			MAX-ACCESS read-write
			STATUS current
			DESCRIPTION
				"Description."
			::= { gOnuCfgSrvPort 17 }

		
--  1.3.6.1.4.1.37950.1.1.6.1.1.7.5
		-- 1.3.6.1.4.1.37950.1.1.6.1.1.7.5
		gOnuCfgPortVlan OBJECT IDENTIFIER ::= { gOnuCfg 5 }

		
--  1.3.6.1.4.1.37950.1.1.6.1.1.7.5.1
		-- 1.3.6.1.4.1.37950.1.1.6.1.1.7.5.1
		gOnuCfgPortVlanPonInx OBJECT-TYPE
			SYNTAX Integer32 (1..16)
			MAX-ACCESS read-write
			STATUS current
			DESCRIPTION
				"Description."
			::= { gOnuCfgPortVlan 1 }

		
--  1.3.6.1.4.1.37950.1.1.6.1.1.7.5.2
		-- 1.3.6.1.4.1.37950.1.1.6.1.1.7.5.2
		gOnuCfgPortVlanOnuInx OBJECT-TYPE
			SYNTAX Integer32 (1..128)
			MAX-ACCESS read-write
			STATUS current
			DESCRIPTION
				"Description."
			::= { gOnuCfgPortVlan 2 }

		
--  1.3.6.1.4.1.37950.1.1.6.1.1.7.5.3
		-- 1.3.6.1.4.1.37950.1.1.6.1.1.7.5.3
		gOnuCfgPortVlanPortType OBJECT-TYPE
			SYNTAX INTEGER
				{
				eth(1),
				wifi(2),
				veip(3)
				}
			MAX-ACCESS read-write
			STATUS current
			DESCRIPTION
				"Description."
			::= { gOnuCfgPortVlan 3 }

		
--  1.3.6.1.4.1.37950.1.1.6.1.1.7.5.4
		-- 1.3.6.1.4.1.37950.1.1.6.1.1.7.5.4
		gOnuCfgPortVlanPortId OBJECT-TYPE
			SYNTAX Integer32 (1..32)
			MAX-ACCESS read-write
			STATUS current
			DESCRIPTION
				"Description."
			::= { gOnuCfgPortVlan 4 }

		
--  1.3.6.1.4.1.37950.1.1.6.1.1.7.5.5
		-- 1.3.6.1.4.1.37950.1.1.6.1.1.7.5.5
		gOnuCfgPortVlanModeType OBJECT-TYPE
			SYNTAX INTEGER
				{
				transparent(1),
				trunk(2),
				tag(3),
				hybrid(4),
				translate(5)
				}
			MAX-ACCESS read-write
			STATUS current
			DESCRIPTION
				"Description."
			::= { gOnuCfgPortVlan 5 }

		
--  1.3.6.1.4.1.37950.1.1.6.1.1.7.5.6
		-- 1.3.6.1.4.1.37950.1.1.6.1.1.7.5.6
		gOnuCfgPortVlanVlanList OBJECT-TYPE
			SYNTAX OCTET STRING
			MAX-ACCESS read-write
			STATUS current
			DESCRIPTION
				"Description."
			::= { gOnuCfgPortVlan 6 }

		
--  1.3.6.1.4.1.37950.1.1.6.1.1.7.5.7
		-- 1.3.6.1.4.1.37950.1.1.6.1.1.7.5.7
		gOnuCfgPortVlanTPri OBJECT-TYPE
			SYNTAX Integer32 (0..8)
			MAX-ACCESS read-write
			STATUS current
			DESCRIPTION
				"Description."
			::= { gOnuCfgPortVlan 7 }

		
--  1.3.6.1.4.1.37950.1.1.6.1.1.7.5.8
		-- 1.3.6.1.4.1.37950.1.1.6.1.1.7.5.8
		gOnuCfgPortVlanDefVlan OBJECT-TYPE
			SYNTAX Integer32 (0..4094)
			MAX-ACCESS read-write
			STATUS current
			DESCRIPTION
				"Description."
			::= { gOnuCfgPortVlan 8 }

		
--  1.3.6.1.4.1.37950.1.1.6.1.1.7.5.9
		-- 1.3.6.1.4.1.37950.1.1.6.1.1.7.5.9
		gOnuCfgPortVlanDefPri OBJECT-TYPE
			SYNTAX Integer32 (0..8)
			MAX-ACCESS read-write
			STATUS current
			DESCRIPTION
				"Description."
			::= { gOnuCfgPortVlan 9 }

		
--  1.3.6.1.4.1.37950.1.1.6.1.1.7.5.10
		-- 1.3.6.1.4.1.37950.1.1.6.1.1.7.5.10
		gOnuCfgPortVlanCVlan OBJECT-TYPE
			SYNTAX Integer32 (0..4094)
			MAX-ACCESS read-write
			STATUS current
			DESCRIPTION
				"Description."
			::= { gOnuCfgPortVlan 10 }

		
--  1.3.6.1.4.1.37950.1.1.6.1.1.7.5.11
		-- 1.3.6.1.4.1.37950.1.1.6.1.1.7.5.11
		gOnuCfgPortVlanCPri OBJECT-TYPE
			SYNTAX Integer32 (0..8)
			MAX-ACCESS read-write
			STATUS current
			DESCRIPTION
				"Description."
			::= { gOnuCfgPortVlan 11 }

		
--  1.3.6.1.4.1.37950.1.1.6.1.1.7.5.12
		-- 1.3.6.1.4.1.37950.1.1.6.1.1.7.5.12
		gOnuCfgPortVlanSVlan OBJECT-TYPE
			SYNTAX Integer32 (0..4094)
			MAX-ACCESS read-write
			STATUS current
			DESCRIPTION
				"Description."
			::= { gOnuCfgPortVlan 12 }

		
--  1.3.6.1.4.1.37950.1.1.6.1.1.7.5.13
		-- 1.3.6.1.4.1.37950.1.1.6.1.1.7.5.13
		gOnuCfgPortVlanSPri OBJECT-TYPE
			SYNTAX Integer32 (0..8)
			MAX-ACCESS read-write
			STATUS current
			DESCRIPTION
				"Description."
			::= { gOnuCfgPortVlan 13 }

		
--  1.3.6.1.4.1.37950.1.1.6.1.1.7.5.14
		-- 1.3.6.1.4.1.37950.1.1.6.1.1.7.5.14
		gOnuCfgPortVlanAction OBJECT-TYPE
			SYNTAX INTEGER
				{
				add(1),
				del(2),
				modify(3)
				}
			MAX-ACCESS read-write
			STATUS current
			DESCRIPTION
				"Description."
			::= { gOnuCfgPortVlan 14 }

		
--  1.3.6.1.4.1.37950.1.1.6.1.1.7.6
		-- 1.3.6.1.4.1.37950.1.1.6.1.1.7.6
		gOnuCfgMVlan OBJECT IDENTIFIER ::= { gOnuCfg 6 }

		
--  1.3.6.1.4.1.37950.1.1.6.1.1.7.6.1
		-- 1.3.6.1.4.1.37950.1.1.6.1.1.7.6.1
		gOnuCfgMVlanPonInx OBJECT-TYPE
			SYNTAX Integer32 (1..16)
			MAX-ACCESS read-write
			STATUS current
			DESCRIPTION
				"Description."
			::= { gOnuCfgMVlan 1 }

		
--  1.3.6.1.4.1.37950.1.1.6.1.1.7.6.2
		-- 1.3.6.1.4.1.37950.1.1.6.1.1.7.6.2
		gOnuCfgMVlanOnuInx OBJECT-TYPE
			SYNTAX Integer32 (1..128)
			MAX-ACCESS read-write
			STATUS current
			DESCRIPTION
				"Description."
			::= { gOnuCfgMVlan 2 }

		
--  1.3.6.1.4.1.37950.1.1.6.1.1.7.6.3
		-- 1.3.6.1.4.1.37950.1.1.6.1.1.7.6.3
		gOnuCfgMVlanList OBJECT-TYPE
			SYNTAX OCTET STRING
			MAX-ACCESS read-write
			STATUS current
			DESCRIPTION
				"Description."
			::= { gOnuCfgMVlan 3 }

		
--  1.3.6.1.4.1.37950.1.1.6.1.1.7.6.4
		-- 1.3.6.1.4.1.37950.1.1.6.1.1.7.6.4
		gOnuCfgMVlanAction OBJECT-TYPE
			SYNTAX INTEGER
				{
				add(1),
				deleAll(2),
				del(3)
				}
			MAX-ACCESS read-write
			STATUS current
			DESCRIPTION
				"Description."
			::= { gOnuCfgMVlan 4 }

		
--  1.3.6.1.4.1.37950.1.1.6.1.1.7.7
		-- 1.3.6.1.4.1.37950.1.1.6.1.1.7.7
		gOnuCfgMVlanStrip OBJECT IDENTIFIER ::= { gOnuCfg 7 }

		
--  1.3.6.1.4.1.37950.1.1.6.1.1.7.7.1
		-- 1.3.6.1.4.1.37950.1.1.6.1.1.7.7.1
		gOnuCfgMVlanStripPonInx OBJECT-TYPE
			SYNTAX Integer32 (1..16)
			MAX-ACCESS read-write
			STATUS current
			DESCRIPTION
				"Description."
			::= { gOnuCfgMVlanStrip 1 }

		
--  1.3.6.1.4.1.37950.1.1.6.1.1.7.7.2
		-- 1.3.6.1.4.1.37950.1.1.6.1.1.7.7.2
		gOnuCfgMVlanStripOnuInx OBJECT-TYPE
			SYNTAX Integer32 (1..128)
			MAX-ACCESS read-write
			STATUS current
			DESCRIPTION
				"Description."
			::= { gOnuCfgMVlanStrip 2 }

		
--  1.3.6.1.4.1.37950.1.1.6.1.1.7.7.3
		-- 1.3.6.1.4.1.37950.1.1.6.1.1.7.7.3
		gOnuCfgMVlanStripPortType OBJECT-TYPE
			SYNTAX INTEGER
				{
				eth(1),
				wifi(2),
				veip(3)
				}
			MAX-ACCESS read-write
			STATUS current
			DESCRIPTION
				"Description."
			::= { gOnuCfgMVlanStrip 3 }

		
--  1.3.6.1.4.1.37950.1.1.6.1.1.7.7.4
		-- 1.3.6.1.4.1.37950.1.1.6.1.1.7.7.4
		gOnuCfgMVlanStripPortId OBJECT-TYPE
			SYNTAX Integer32 (1..32)
			MAX-ACCESS read-write
			STATUS current
			DESCRIPTION
				"Description."
			::= { gOnuCfgMVlanStrip 4 }

		
--  1.3.6.1.4.1.37950.1.1.6.1.1.7.7.5
		-- 1.3.6.1.4.1.37950.1.1.6.1.1.7.7.5
		gOnuCfgMVlanStripTransList OBJECT-TYPE
			SYNTAX OCTET STRING
			MAX-ACCESS read-write
			STATUS current
			DESCRIPTION
				"Description."
			::= { gOnuCfgMVlanStrip 5 }

		
--  1.3.6.1.4.1.37950.1.1.6.1.1.7.7.6
		-- 1.3.6.1.4.1.37950.1.1.6.1.1.7.7.6
		gOnuCfgMVlanStripAction OBJECT-TYPE
			SYNTAX INTEGER
				{
				add(1),
				del(2),
				modify(3)
				}
			MAX-ACCESS read-write
			STATUS current
			DESCRIPTION
				"Description."
			::= { gOnuCfgMVlanStrip 6 }

		
--  1.3.6.1.4.1.37950.1.1.6.1.1.7.8
		-- 1.3.6.1.4.1.37950.1.1.6.1.1.7.8
		gOnuCfgPort OBJECT IDENTIFIER ::= { gOnuCfg 8 }

		
--  1.3.6.1.4.1.37950.1.1.6.1.1.7.8.1
		-- 1.3.6.1.4.1.37950.1.1.6.1.1.7.8.1
		gOnuCfgPortPonInx OBJECT-TYPE
			SYNTAX Integer32 (1..16)
			MAX-ACCESS read-write
			STATUS current
			DESCRIPTION
				"Description."
			::= { gOnuCfgPort 1 }

		
--  1.3.6.1.4.1.37950.1.1.6.1.1.7.8.2
		-- 1.3.6.1.4.1.37950.1.1.6.1.1.7.8.2
		gOnuCfgPortOnuInx OBJECT-TYPE
			SYNTAX Integer32 (1..128)
			MAX-ACCESS read-write
			STATUS current
			DESCRIPTION
				"Description."
			::= { gOnuCfgPort 2 }

		
--  1.3.6.1.4.1.37950.1.1.6.1.1.7.8.3
		-- 1.3.6.1.4.1.37950.1.1.6.1.1.7.8.3
		gOnuCfgPortId OBJECT-TYPE
			SYNTAX Integer32
			MAX-ACCESS read-write
			STATUS current
			DESCRIPTION
				"Description."
			::= { gOnuCfgPort 3 }

		
--  1.3.6.1.4.1.37950.1.1.6.1.1.7.8.4
		-- 1.3.6.1.4.1.37950.1.1.6.1.1.7.8.4
		gOnuCfgPortEnable OBJECT-TYPE
			SYNTAX INTEGER
				{
				enable(0),
				disable(1)
				}
			MAX-ACCESS read-write
			STATUS current
			DESCRIPTION
				"Description."
			::= { gOnuCfgPort 4 }

		
--  1.3.6.1.4.1.37950.1.1.6.1.1.7.8.5
		-- 1.3.6.1.4.1.37950.1.1.6.1.1.7.8.5
		gOnuCfgPortLoopDetect OBJECT-TYPE
			SYNTAX INTEGER
				{
				enable(0),
				disable(1)
				}
			MAX-ACCESS read-write
			STATUS current
			DESCRIPTION
				"Description."
			::= { gOnuCfgPort 5 }

		
--  1.3.6.1.4.1.37950.1.1.6.1.1.7.8.6
		-- 1.3.6.1.4.1.37950.1.1.6.1.1.7.8.6
		gOnuCfgPortSpeed OBJECT-TYPE
			SYNTAX INTEGER
				{
				auto(1),
				half-10(2),
				full-10(3),
				half-100(4),
				full-100(5),
				full-1000(6),
				half-1000(7),
				full-10g(8),
				full-2point5g(9),
				full-5g(10),
				full-25g(11),
				full-40g(12)
				}
			MAX-ACCESS read-write
			STATUS current
			DESCRIPTION
				"Description."
			::= { gOnuCfgPort 6 }

		
--  1.3.6.1.4.1.37950.1.1.6.1.1.7.8.7
		-- 1.3.6.1.4.1.37950.1.1.6.1.1.7.8.7
		gOnuCfgPortAction OBJECT-TYPE
			SYNTAX INTEGER { submit(1) }
			MAX-ACCESS read-write
			STATUS current
			DESCRIPTION
				"Description."
			::= { gOnuCfgPort 7 }

		
--  1.3.6.1.4.1.37950.1.1.6.1.1.7.8.8
		-- 1.3.6.1.4.1.37950.1.1.6.1.1.7.8.8
		gOnuCfgPortMacLimit OBJECT-TYPE
			SYNTAX Integer32 (0..255)
			MAX-ACCESS read-write
			STATUS current
			DESCRIPTION
				"Description."
			DEFVAL { '0'b }
			::= { gOnuCfgPort 8 }

		
--  1.3.6.1.4.1.37950.1.1.6.1.1.7.9
		-- 1.3.6.1.4.1.37950.1.1.6.1.1.7.9
		gOnuCfgIphost OBJECT IDENTIFIER ::= { gOnuCfg 9 }

		
--  1.3.6.1.4.1.37950.1.1.6.1.1.7.9.1
		-- 1.3.6.1.4.1.37950.1.1.6.1.1.7.9.1
		gOnuCfgIphostPonInx OBJECT-TYPE
			SYNTAX Integer32 (1..16)
			MAX-ACCESS read-write
			STATUS current
			DESCRIPTION
				"Description."
			::= { gOnuCfgIphost 1 }

		
--  1.3.6.1.4.1.37950.1.1.6.1.1.7.9.2
		-- 1.3.6.1.4.1.37950.1.1.6.1.1.7.9.2
		gOnuCfgIphostOnuInx OBJECT-TYPE
			SYNTAX Integer32 (1..128)
			MAX-ACCESS read-write
			STATUS current
			DESCRIPTION
				"Description."
			::= { gOnuCfgIphost 2 }

		
--  1.3.6.1.4.1.37950.1.1.6.1.1.7.9.3
		-- 1.3.6.1.4.1.37950.1.1.6.1.1.7.9.3
		gOnuCfgIphostId OBJECT-TYPE
			SYNTAX Integer32
			MAX-ACCESS read-write
			STATUS current
			DESCRIPTION
				"Description."
			::= { gOnuCfgIphost 3 }

		
--  1.3.6.1.4.1.37950.1.1.6.1.1.7.9.4
		-- 1.3.6.1.4.1.37950.1.1.6.1.1.7.9.4
		gOnuCfgIphostDesc OBJECT-TYPE
			SYNTAX OCTET STRING
			MAX-ACCESS read-write
			STATUS current
			DESCRIPTION
				"Description."
			::= { gOnuCfgIphost 4 }

		
--  1.3.6.1.4.1.37950.1.1.6.1.1.7.9.5
		-- 1.3.6.1.4.1.37950.1.1.6.1.1.7.9.5
		gOnuCfgIphostIpMode OBJECT-TYPE
			SYNTAX INTEGER
				{
				dhcp(1),
				static_ip(2)
				}
			MAX-ACCESS read-write
			STATUS current
			DESCRIPTION
				"Description."
			::= { gOnuCfgIphost 5 }

		
--  1.3.6.1.4.1.37950.1.1.6.1.1.7.9.6
		-- 1.3.6.1.4.1.37950.1.1.6.1.1.7.9.6
		gOnuCfgIphostIpAddr OBJECT-TYPE
			SYNTAX IpAddress
			MAX-ACCESS read-write
			STATUS current
			DESCRIPTION
				"Description."
			::= { gOnuCfgIphost 6 }

		
--  1.3.6.1.4.1.37950.1.1.6.1.1.7.9.7
		-- 1.3.6.1.4.1.37950.1.1.6.1.1.7.9.7
		gOnuCfgIphostMask OBJECT-TYPE
			SYNTAX IpAddress
			MAX-ACCESS read-write
			STATUS current
			DESCRIPTION
				"Description."
			::= { gOnuCfgIphost 7 }

		
--  1.3.6.1.4.1.37950.1.1.6.1.1.7.9.8
		-- 1.3.6.1.4.1.37950.1.1.6.1.1.7.9.8
		gOnuCfgIphostGateway OBJECT-TYPE
			SYNTAX IpAddress
			MAX-ACCESS read-write
			STATUS current
			DESCRIPTION
				"Description."
			::= { gOnuCfgIphost 8 }

		
--  1.3.6.1.4.1.37950.1.1.6.1.1.7.9.9
		-- 1.3.6.1.4.1.37950.1.1.6.1.1.7.9.9
		gOnuCfgIphostDns1 OBJECT-TYPE
			SYNTAX IpAddress
			MAX-ACCESS read-write
			STATUS current
			DESCRIPTION
				"Description."
			::= { gOnuCfgIphost 9 }

		
--  1.3.6.1.4.1.37950.1.1.6.1.1.7.9.10
		-- 1.3.6.1.4.1.37950.1.1.6.1.1.7.9.10
		gOnuCfgIphostDns2 OBJECT-TYPE
			SYNTAX IpAddress
			MAX-ACCESS read-write
			STATUS current
			DESCRIPTION
				"Description."
			::= { gOnuCfgIphost 10 }

		
--  1.3.6.1.4.1.37950.1.1.6.1.1.7.9.11
		-- 1.3.6.1.4.1.37950.1.1.6.1.1.7.9.11
		gOnuCfgIphostAction OBJECT-TYPE
			SYNTAX INTEGER
				{
				add(0),
				delete(1)
				}
			MAX-ACCESS read-write
			STATUS current
			DESCRIPTION
				"Description."
			::= { gOnuCfgIphost 11 }

		
--  1.3.6.1.4.1.37950.1.1.6.1.1.7.10
		-- 1.3.6.1.4.1.37950.1.1.6.1.1.7.10
		gOnuCfgIgmpMaxGroup OBJECT IDENTIFIER ::= { gOnuCfg 10 }

		
--  1.3.6.1.4.1.37950.1.1.6.1.1.7.10.1
		-- 1.3.6.1.4.1.37950.1.1.6.1.1.7.10.1
		gOnuCfgIgmpMPonlnx OBJECT-TYPE
			SYNTAX Integer32 (1..16)
			MAX-ACCESS read-write
			STATUS current
			DESCRIPTION
				"Description."
			::= { gOnuCfgIgmpMaxGroup 1 }

		
--  1.3.6.1.4.1.37950.1.1.6.1.1.7.10.2
		-- 1.3.6.1.4.1.37950.1.1.6.1.1.7.10.2
		gOnuCfgIgmpMOnulnx OBJECT-TYPE
			SYNTAX Integer32
			MAX-ACCESS read-write
			STATUS current
			DESCRIPTION
				"Description."
			::= { gOnuCfgIgmpMaxGroup 2 }

		
--  1.3.6.1.4.1.37950.1.1.6.1.1.7.10.3
		-- 1.3.6.1.4.1.37950.1.1.6.1.1.7.10.3
		gOnuCfgIgmpMPortType OBJECT-TYPE
			SYNTAX INTEGER
				{
				eth(0),
				veip(1)
				}
			MAX-ACCESS read-write
			STATUS current
			DESCRIPTION
				"Description."
			::= { gOnuCfgIgmpMaxGroup 3 }

		
--  1.3.6.1.4.1.37950.1.1.6.1.1.7.10.4
		-- 1.3.6.1.4.1.37950.1.1.6.1.1.7.10.4
		gOnuCfgIgmpMPortId OBJECT-TYPE
			SYNTAX Integer32 (1..32)
			MAX-ACCESS read-write
			STATUS current
			DESCRIPTION
				"Description."
			::= { gOnuCfgIgmpMaxGroup 4 }

		
--  1.3.6.1.4.1.37950.1.1.6.1.1.7.10.5
		-- 1.3.6.1.4.1.37950.1.1.6.1.1.7.10.5
		gOnuCfgIgmpMGroup OBJECT-TYPE
			SYNTAX Integer32 (0..65535)
			MAX-ACCESS read-write
			STATUS current
			DESCRIPTION
				"Description."
			::= { gOnuCfgIgmpMaxGroup 5 }

		
--  1.3.6.1.4.1.37950.1.1.6.1.1.7.10.6
		-- 1.3.6.1.4.1.37950.1.1.6.1.1.7.10.6
		gOnuCfgIgmpMAction OBJECT-TYPE
			SYNTAX INTEGER { add(1) }
			MAX-ACCESS read-write
			STATUS current
			DESCRIPTION
				"Description."
			::= { gOnuCfgIgmpMaxGroup 6 }

		
--  1.3.6.1.4.1.37950.1.1.6.1.1.7.11
		-- 1.3.6.1.4.1.37950.1.1.6.1.1.7.11
		gOnuCfgIgmpBandwidth OBJECT IDENTIFIER ::= { gOnuCfg 11 }

		
--  1.3.6.1.4.1.37950.1.1.6.1.1.7.11.1
		-- 1.3.6.1.4.1.37950.1.1.6.1.1.7.11.1
		gOnuCfgIgmpBPonlnx OBJECT-TYPE
			SYNTAX Integer32 (1..16)
			MAX-ACCESS read-write
			STATUS current
			DESCRIPTION
				"Description."
			::= { gOnuCfgIgmpBandwidth 1 }

		
--  1.3.6.1.4.1.37950.1.1.6.1.1.7.11.2
		-- 1.3.6.1.4.1.37950.1.1.6.1.1.7.11.2
		gOnuCfgIgmpBOnulnx OBJECT-TYPE
			SYNTAX Integer32
			MAX-ACCESS read-write
			STATUS current
			DESCRIPTION
				"Description."
			::= { gOnuCfgIgmpBandwidth 2 }

		
--  1.3.6.1.4.1.37950.1.1.6.1.1.7.11.3
		-- 1.3.6.1.4.1.37950.1.1.6.1.1.7.11.3
		gOnuCfgIgmpBPortType OBJECT-TYPE
			SYNTAX INTEGER
				{
				eth(0),
				veip(1)
				}
			MAX-ACCESS read-write
			STATUS current
			DESCRIPTION
				"Description."
			::= { gOnuCfgIgmpBandwidth 3 }

		
--  1.3.6.1.4.1.37950.1.1.6.1.1.7.11.4
		-- 1.3.6.1.4.1.37950.1.1.6.1.1.7.11.4
		gOnuCfgIgmpBPortId OBJECT-TYPE
			SYNTAX Integer32 (1..32)
			MAX-ACCESS read-write
			STATUS current
			DESCRIPTION
				"Description."
			::= { gOnuCfgIgmpBandwidth 4 }

		
--  1.3.6.1.4.1.37950.1.1.6.1.1.7.11.5
		-- 1.3.6.1.4.1.37950.1.1.6.1.1.7.11.5
		gOnuCfgIgmpBWidth OBJECT-TYPE
			SYNTAX Unsigned32 (0..4294967295)
			MAX-ACCESS read-write
			STATUS current
			DESCRIPTION
				"Description."
			::= { gOnuCfgIgmpBandwidth 5 }

		
--  1.3.6.1.4.1.37950.1.1.6.1.1.7.11.6
		-- 1.3.6.1.4.1.37950.1.1.6.1.1.7.11.6
		gOnuCfgIgmpBEnforce OBJECT-TYPE
			SYNTAX INTEGER
				{
				disable(0),
				enable(1)
				}
			MAX-ACCESS read-write
			STATUS current
			DESCRIPTION
				"Description."
			::= { gOnuCfgIgmpBandwidth 6 }

		
--  1.3.6.1.4.1.37950.1.1.6.1.1.7.11.7
		-- 1.3.6.1.4.1.37950.1.1.6.1.1.7.11.7
		gOnuCfgIgmpBAction OBJECT-TYPE
			SYNTAX INTEGER { add(1) }
			MAX-ACCESS read-write
			STATUS current
			DESCRIPTION
				"Description."
			::= { gOnuCfgIgmpBandwidth 7 }

		
--  1.3.6.1.4.1.37950.1.1.6.1.1.7.12
		-- 1.3.6.1.4.1.37950.1.1.6.1.1.7.12
		gOnuCfgIgmpBindProfile OBJECT IDENTIFIER ::= { gOnuCfg 12 }

		
--  1.3.6.1.4.1.37950.1.1.6.1.1.7.12.1
		-- 1.3.6.1.4.1.37950.1.1.6.1.1.7.12.1
		gOnuCfgIgmpPPonlnx OBJECT-TYPE
			SYNTAX Integer32 (1..16)
			MAX-ACCESS read-write
			STATUS current
			DESCRIPTION
				"Description."
			::= { gOnuCfgIgmpBindProfile 1 }

		
--  1.3.6.1.4.1.37950.1.1.6.1.1.7.12.2
		-- 1.3.6.1.4.1.37950.1.1.6.1.1.7.12.2
		gOnuCfgIgmpPOnulnx OBJECT-TYPE
			SYNTAX Integer32
			MAX-ACCESS read-write
			STATUS current
			DESCRIPTION
				"Description."
			::= { gOnuCfgIgmpBindProfile 2 }

		
--  1.3.6.1.4.1.37950.1.1.6.1.1.7.12.3
		-- 1.3.6.1.4.1.37950.1.1.6.1.1.7.12.3
		gOnuCfgIgmpPPortType OBJECT-TYPE
			SYNTAX INTEGER
				{
				eth(0),
				veip(1)
				}
			MAX-ACCESS read-write
			STATUS current
			DESCRIPTION
				"Description."
			::= { gOnuCfgIgmpBindProfile 3 }

		
--  1.3.6.1.4.1.37950.1.1.6.1.1.7.12.4
		-- 1.3.6.1.4.1.37950.1.1.6.1.1.7.12.4
		gOnuCfgIgmpPPortId OBJECT-TYPE
			SYNTAX Integer32 (1..32)
			MAX-ACCESS read-write
			STATUS current
			DESCRIPTION
				"Description."
			::= { gOnuCfgIgmpBindProfile 4 }

		
--  1.3.6.1.4.1.37950.1.1.6.1.1.7.12.5
		-- 1.3.6.1.4.1.37950.1.1.6.1.1.7.12.5
		gOnuCfgIgmpPProfileName OBJECT-TYPE
			SYNTAX OCTET STRING
			MAX-ACCESS read-write
			STATUS current
			DESCRIPTION
				"Description."
			::= { gOnuCfgIgmpBindProfile 5 }

		
--  1.3.6.1.4.1.37950.1.1.6.1.1.7.12.6
		-- 1.3.6.1.4.1.37950.1.1.6.1.1.7.12.6
		gOnuCfgIgmpPAction OBJECT-TYPE
			SYNTAX INTEGER
				{
				add(1),
				del(2)
				}
			MAX-ACCESS read-write
			STATUS current
			DESCRIPTION
				"Description."
			::= { gOnuCfgIgmpBindProfile 6 }

		
--  1.3.6.1.4.1.37950.1.1.6.1.1.7.13
		-- 1.3.6.1.4.1.37950.1.1.6.1.1.7.13
		gOnuCfgIgmpInfoGet OBJECT IDENTIFIER ::= { gOnuCfg 13 }

		
--  1.3.6.1.4.1.37950.1.1.6.1.1.7.13.1
		-- 1.3.6.1.4.1.37950.1.1.6.1.1.7.13.1
		gIgmpPon OBJECT-TYPE
			SYNTAX Integer32
			MAX-ACCESS read-write
			STATUS current
			DESCRIPTION
				"Description."
			::= { gOnuCfgIgmpInfoGet 1 }

		
--  1.3.6.1.4.1.37950.1.1.6.1.1.7.13.2
		-- 1.3.6.1.4.1.37950.1.1.6.1.1.7.13.2
		gIgmpOnu OBJECT-TYPE
			SYNTAX Integer32
			MAX-ACCESS read-write
			STATUS current
			DESCRIPTION
				"Description."
			::= { gOnuCfgIgmpInfoGet 2 }

		
--  1.3.6.1.4.1.37950.1.1.6.1.1.7.13.3
		-- 1.3.6.1.4.1.37950.1.1.6.1.1.7.13.3
		gIgmpPortId OBJECT-TYPE
			SYNTAX Integer32
			MAX-ACCESS read-write
			STATUS current
			DESCRIPTION
				"Description."
			::= { gOnuCfgIgmpInfoGet 3 }

		
--  1.3.6.1.4.1.37950.1.1.6.1.1.7.13.4
		-- 1.3.6.1.4.1.37950.1.1.6.1.1.7.13.4
		gIgmpTotalNum OBJECT-TYPE
			SYNTAX Integer32
			MAX-ACCESS read-write
			STATUS current
			DESCRIPTION
				"Description."
			::= { gOnuCfgIgmpInfoGet 4 }

		
--  1.3.6.1.4.1.37950.1.1.6.1.1.7.13.5
		-- 1.3.6.1.4.1.37950.1.1.6.1.1.7.13.5
		gIgmpInterface OBJECT-TYPE
			SYNTAX OCTET STRING
			MAX-ACCESS read-write
			STATUS current
			DESCRIPTION
				"Description."
			::= { gOnuCfgIgmpInfoGet 5 }

		
--  1.3.6.1.4.1.37950.1.1.6.1.1.7.13.6
		-- 1.3.6.1.4.1.37950.1.1.6.1.1.7.13.6
		gIgmpMaxGroups OBJECT-TYPE
			SYNTAX Integer32
			MAX-ACCESS read-write
			STATUS current
			DESCRIPTION
				"Description."
			::= { gOnuCfgIgmpInfoGet 6 }

		
--  1.3.6.1.4.1.37950.1.1.6.1.1.7.13.7
		-- 1.3.6.1.4.1.37950.1.1.6.1.1.7.13.7
		gIgmpMaxBandwidth OBJECT-TYPE
			SYNTAX Unsigned32
			MAX-ACCESS read-write
			STATUS current
			DESCRIPTION
				"Description."
			::= { gOnuCfgIgmpInfoGet 7 }

		
--  1.3.6.1.4.1.37950.1.1.6.1.1.7.13.8
		-- 1.3.6.1.4.1.37950.1.1.6.1.1.7.13.8
		gIgmpEnforce OBJECT-TYPE
			SYNTAX INTEGER
				{
				disable(0),
				enable(1)
				}
			MAX-ACCESS read-write
			STATUS current
			DESCRIPTION
				"Description."
			::= { gOnuCfgIgmpInfoGet 8 }

		
--  1.3.6.1.4.1.37950.1.1.6.1.1.7.13.9
		-- 1.3.6.1.4.1.37950.1.1.6.1.1.7.13.9
		gIgmpProfile OBJECT-TYPE
			SYNTAX OCTET STRING
			MAX-ACCESS read-write
			STATUS current
			DESCRIPTION
				"Description."
			::= { gOnuCfgIgmpInfoGet 9 }

		
--  1.3.6.1.4.1.37950.1.1.6.1.1.7.14
		-- 1.3.6.1.4.1.37950.1.1.6.1.1.7.14
		gOnuCfgRateLimit OBJECT IDENTIFIER ::= { gOnuCfg 14 }

		
--  1.3.6.1.4.1.37950.1.1.6.1.1.7.14.1
		-- 1.3.6.1.4.1.37950.1.1.6.1.1.7.14.1
		gOnuCfgRateLimitPonInx OBJECT-TYPE
			SYNTAX Integer32 (1..16)
			MAX-ACCESS read-write
			STATUS current
			DESCRIPTION
				"Description."
			::= { gOnuCfgRateLimit 1 }

		
--  1.3.6.1.4.1.37950.1.1.6.1.1.7.14.2
		-- 1.3.6.1.4.1.37950.1.1.6.1.1.7.14.2
		gOnuCfgRateLimitOnuInx OBJECT-TYPE
			SYNTAX Integer32 (1..128)
			MAX-ACCESS read-write
			STATUS current
			DESCRIPTION
				"Description."
			::= { gOnuCfgRateLimit 2 }

		
--  1.3.6.1.4.1.37950.1.1.6.1.1.7.14.3
		-- 1.3.6.1.4.1.37950.1.1.6.1.1.7.14.3
		gOnuCfgRateLimitPortId OBJECT-TYPE
			SYNTAX Integer32
			MAX-ACCESS read-write
			STATUS current
			DESCRIPTION
				"Description."
			::= { gOnuCfgRateLimit 3 }

		
--  1.3.6.1.4.1.37950.1.1.6.1.1.7.14.4
		-- 1.3.6.1.4.1.37950.1.1.6.1.1.7.14.4
		gOnuCfgRateLimitType OBJECT-TYPE
			SYNTAX INTEGER (0..4)
			MAX-ACCESS read-write
			STATUS current
			DESCRIPTION
				"Description."
			::= { gOnuCfgRateLimit 4 }

		
--  1.3.6.1.4.1.37950.1.1.6.1.1.7.14.5
		-- 1.3.6.1.4.1.37950.1.1.6.1.1.7.14.5
		gOnuCfgRateLimitUpsCir OBJECT-TYPE
			SYNTAX Unsigned32 (0..4294967295)
			MAX-ACCESS read-write
			STATUS current
			DESCRIPTION
				"Description."
			::= { gOnuCfgRateLimit 5 }

		
--  1.3.6.1.4.1.37950.1.1.6.1.1.7.14.6
		-- 1.3.6.1.4.1.37950.1.1.6.1.1.7.14.6
		gOnuCfgRateLimitUpsPir OBJECT-TYPE
			SYNTAX Unsigned32 (0..4294967295)
			MAX-ACCESS read-write
			STATUS current
			DESCRIPTION
				"Description."
			::= { gOnuCfgRateLimit 6 }

		
--  1.3.6.1.4.1.37950.1.1.6.1.1.7.14.7
		-- 1.3.6.1.4.1.37950.1.1.6.1.1.7.14.7
		gOnuCfgRateLimitDnsCir OBJECT-TYPE
			SYNTAX Unsigned32 (0..4294967295)
			MAX-ACCESS read-write
			STATUS current
			DESCRIPTION
				"Description."
			::= { gOnuCfgRateLimit 7 }

		
--  1.3.6.1.4.1.37950.1.1.6.1.1.7.14.8
		-- 1.3.6.1.4.1.37950.1.1.6.1.1.7.14.8
		gOnuCfgRateLimitDnsPir OBJECT-TYPE
			SYNTAX Unsigned32 (0..4294967295)
			MAX-ACCESS read-write
			STATUS current
			DESCRIPTION
				"Description."
			::= { gOnuCfgRateLimit 8 }

		
--  1.3.6.1.4.1.37950.1.1.6.1.1.7.14.9
		-- 1.3.6.1.4.1.37950.1.1.6.1.1.7.14.9
		gOnuCfgRateLimitAction OBJECT-TYPE
			SYNTAX INTEGER { submit(1) }
			MAX-ACCESS read-write
			STATUS current
			DESCRIPTION
				"Description."
			::= { gOnuCfgRateLimit 9 }

		
--  1.3.6.1.4.1.37950.1.1.6.1.1.7.15
		-- 1.3.6.1.4.1.37950.1.1.6.1.1.7.15
		gOnuCfgMacLimit OBJECT IDENTIFIER ::= { gOnuCfg 15 }

		
--  1.3.6.1.4.1.37950.1.1.6.1.1.7.15.1
		-- 1.3.6.1.4.1.37950.1.1.6.1.1.7.15.1
		gOnuCfgMacLimitPonInx OBJECT-TYPE
			SYNTAX Integer32 (1..16)
			MAX-ACCESS read-write
			STATUS current
			DESCRIPTION
				"Description."
			::= { gOnuCfgMacLimit 1 }

		
--  1.3.6.1.4.1.37950.1.1.6.1.1.7.15.2
		-- 1.3.6.1.4.1.37950.1.1.6.1.1.7.15.2
		gOnuCfgMacLimitOnuInx OBJECT-TYPE
			SYNTAX Integer32 (1..128)
			MAX-ACCESS read-write
			STATUS current
			DESCRIPTION
				"Description."
			::= { gOnuCfgMacLimit 2 }

		
--  1.3.6.1.4.1.37950.1.1.6.1.1.7.15.3
		-- 1.3.6.1.4.1.37950.1.1.6.1.1.7.15.3
		gOnuCfgMacLimitVal OBJECT-TYPE
			SYNTAX Integer32 (0..255)
			MAX-ACCESS read-write
			STATUS current
			DESCRIPTION
				"Description."
			DEFVAL { '0'b }
			::= { gOnuCfgMacLimit 3 }

		
--  1.3.6.1.4.1.37950.1.1.6.1.1.7.15.4
		-- 1.3.6.1.4.1.37950.1.1.6.1.1.7.15.4
		gOnuCfgMacLimitAction OBJECT-TYPE
			SYNTAX INTEGER { submit(1) }
			MAX-ACCESS read-write
			STATUS current
			DESCRIPTION
				"Description."
			::= { gOnuCfgMacLimit 4 }

		
--  1.3.6.1.4.1.37950.1.1.6.1.1.7.16
		-- 1.3.6.1.4.1.37950.1.1.6.1.1.7.16
		gOnuCfgRateLimitTable OBJECT-TYPE
			SYNTAX SEQUENCE OF GOnuCfgRateLimitEntry
			MAX-ACCESS not-accessible
			STATUS current
			DESCRIPTION
				"Description."
			::= { gOnuCfg 16 }

		
--  1.3.6.1.4.1.37950.1.1.6.1.1.7.16.1
		-- 1.3.6.1.4.1.37950.1.1.6.1.1.7.16.1
		gOnuCfgRateLimitEntry OBJECT-TYPE
			SYNTAX GOnuCfgRateLimitEntry
			MAX-ACCESS not-accessible
			STATUS current
			DESCRIPTION
				"Description."
			INDEX { gOnuCfgRateLimitTablePonInx, gOnuCfgRateLimitTableOnuInx, gOnuCfgRateLimitTablePortId }
			::= { gOnuCfgRateLimitTable 1 }

		
		GOnuCfgRateLimitEntry ::=
			SEQUENCE { 
				gOnuCfgRateLimitTablePonInx
					Integer32,
				gOnuCfgRateLimitTableOnuInx
					Integer32,
				gOnuCfgRateLimitTablePortId
					Integer32,
				gOnuCfgRateLimitTableSpeedStatus
					INTEGER,
				gOnuCfgRateLimitTableSpeedConfig
					INTEGER,
				gOnuCfgRateLimitTableLinkStatus
					INTEGER,
				gOnuCfgRateLimitTableAdminStatus
					INTEGER,
				gOnuCfgRateLimitTableLOOPstatus
					INTEGER,
				gOnuCfgRateLimitTableMacLimit
					Integer32,
				gOnuCfgRateLimitTableMaxFrame
					Unsigned32,
				gOnuCfgRateLimitTableUpsCir
					Unsigned32,
				gOnuCfgRateLimitTableUpsPir
					Unsigned32,
				gOnuCfgRateLimitTableDnsCir
					Unsigned32,
				gOnuCfgRateLimitTableDnsPir
					Unsigned32
			 }

--  1.3.6.1.4.1.37950.1.1.6.1.1.7.16.1.1
		-- 1.3.6.1.4.1.37950.1.1.6.1.1.7.16.1.1
		gOnuCfgRateLimitTablePonInx OBJECT-TYPE
			SYNTAX Integer32 (1..16)
			MAX-ACCESS read-only
			STATUS current
			DESCRIPTION
				"Description."
			::= { gOnuCfgRateLimitEntry 1 }

		
--  1.3.6.1.4.1.37950.1.1.6.1.1.7.16.1.2
		-- 1.3.6.1.4.1.37950.1.1.6.1.1.7.16.1.2
		gOnuCfgRateLimitTableOnuInx OBJECT-TYPE
			SYNTAX Integer32 (1..128)
			MAX-ACCESS read-only
			STATUS current
			DESCRIPTION
				"Description."
			::= { gOnuCfgRateLimitEntry 2 }

		
--  1.3.6.1.4.1.37950.1.1.6.1.1.7.16.1.3
		-- 1.3.6.1.4.1.37950.1.1.6.1.1.7.16.1.3
		gOnuCfgRateLimitTablePortId OBJECT-TYPE
			SYNTAX Integer32
			MAX-ACCESS read-only
			STATUS current
			DESCRIPTION
				"Description."
			::= { gOnuCfgRateLimitEntry 3 }

		
--  1.3.6.1.4.1.37950.1.1.6.1.1.7.16.1.4
		-- 1.3.6.1.4.1.37950.1.1.6.1.1.7.16.1.4
		gOnuCfgRateLimitTableSpeedStatus OBJECT-TYPE
			SYNTAX INTEGER
				{
				auto(0),
				full-10(1),
				full-100(2),
				full-1000(3),
				half-10(4),
				half-100(5),
				half-1000(6),
				unknown(7),
				full-10g(8),
				full-2point5g(9),
				full-5g(10),
				full-25g(11),
				full-40g(12)
				}
			MAX-ACCESS read-only
			STATUS current
			DESCRIPTION
				"Description."
			::= { gOnuCfgRateLimitEntry 4 }

		
--  1.3.6.1.4.1.37950.1.1.6.1.1.7.16.1.5
		-- 1.3.6.1.4.1.37950.1.1.6.1.1.7.16.1.5
		gOnuCfgRateLimitTableSpeedConfig OBJECT-TYPE
			SYNTAX INTEGER
				{
				auto(0),
				full-10(1),
				full-100(2),
				full-1000(3),
				half-10(4),
				half-100(5),
				half-1000(6),
				unknown(7),
				full-10g(8),
				full-2point5g(9),
				full-5g(10),
				full-25g(11),
				full-40g(12)
				}
			MAX-ACCESS read-only
			STATUS current
			DESCRIPTION
				"Description."
			::= { gOnuCfgRateLimitEntry 5 }

		
--  1.3.6.1.4.1.37950.1.1.6.1.1.7.16.1.6
		-- 1.3.6.1.4.1.37950.1.1.6.1.1.7.16.1.6
		gOnuCfgRateLimitTableLinkStatus OBJECT-TYPE
			SYNTAX INTEGER
				{
				up(0),
				down(1),
				unKnown(2)
				}
			MAX-ACCESS read-only
			STATUS current
			DESCRIPTION
				"Description."
			::= { gOnuCfgRateLimitEntry 6 }

		
--  1.3.6.1.4.1.37950.1.1.6.1.1.7.16.1.7
		-- 1.3.6.1.4.1.37950.1.1.6.1.1.7.16.1.7
		gOnuCfgRateLimitTableAdminStatus OBJECT-TYPE
			SYNTAX INTEGER
				{
				enable(0),
				disable(1),
				unKnown(3)
				}
			MAX-ACCESS read-only
			STATUS current
			DESCRIPTION
				"Description."
			::= { gOnuCfgRateLimitEntry 7 }

		
--  1.3.6.1.4.1.37950.1.1.6.1.1.7.16.1.8
		-- 1.3.6.1.4.1.37950.1.1.6.1.1.7.16.1.8
		gOnuCfgRateLimitTableLOOPstatus OBJECT-TYPE
			SYNTAX INTEGER
				{
				disable(0),
				none(1),
				none1(2),
				enable(3),
				unKnown(4)
				}
			MAX-ACCESS read-only
			STATUS current
			DESCRIPTION
				"Description."
			::= { gOnuCfgRateLimitEntry 8 }

		
--  1.3.6.1.4.1.37950.1.1.6.1.1.7.16.1.9
		-- 1.3.6.1.4.1.37950.1.1.6.1.1.7.16.1.9
		gOnuCfgRateLimitTableMacLimit OBJECT-TYPE
			SYNTAX Integer32 (0..255)
			MAX-ACCESS read-only
			STATUS current
			DESCRIPTION
				"Description."
			::= { gOnuCfgRateLimitEntry 9 }

		
--  1.3.6.1.4.1.37950.1.1.6.1.1.7.16.1.10
		-- 1.3.6.1.4.1.37950.1.1.6.1.1.7.16.1.10
		gOnuCfgRateLimitTableMaxFrame OBJECT-TYPE
			SYNTAX Unsigned32
			MAX-ACCESS read-only
			STATUS current
			DESCRIPTION
				"Description."
			::= { gOnuCfgRateLimitEntry 10 }

		
--  1.3.6.1.4.1.37950.1.1.6.1.1.7.16.1.11
		-- 1.3.6.1.4.1.37950.1.1.6.1.1.7.16.1.11
		gOnuCfgRateLimitTableUpsCir OBJECT-TYPE
			SYNTAX Unsigned32 (0..4294967295)
			MAX-ACCESS read-only
			STATUS current
			DESCRIPTION
				"Description."
			::= { gOnuCfgRateLimitEntry 11 }

		
--  1.3.6.1.4.1.37950.1.1.6.1.1.7.16.1.12
		-- 1.3.6.1.4.1.37950.1.1.6.1.1.7.16.1.12
		gOnuCfgRateLimitTableUpsPir OBJECT-TYPE
			SYNTAX Unsigned32 (0..4294967295)
			MAX-ACCESS read-only
			STATUS current
			DESCRIPTION
				"Description."
			::= { gOnuCfgRateLimitEntry 12 }

		
--  1.3.6.1.4.1.37950.1.1.6.1.1.7.16.1.13
		-- 1.3.6.1.4.1.37950.1.1.6.1.1.7.16.1.13
		gOnuCfgRateLimitTableDnsCir OBJECT-TYPE
			SYNTAX Unsigned32 (0..4294967295)
			MAX-ACCESS read-only
			STATUS current
			DESCRIPTION
				"Description."
			::= { gOnuCfgRateLimitEntry 13 }

		
--  1.3.6.1.4.1.37950.1.1.6.1.1.7.16.1.14
		-- 1.3.6.1.4.1.37950.1.1.6.1.1.7.16.1.14
		gOnuCfgRateLimitTableDnsPir OBJECT-TYPE
			SYNTAX Unsigned32 (0..4294967295)
			MAX-ACCESS read-only
			STATUS current
			DESCRIPTION
				"Description."
			::= { gOnuCfgRateLimitEntry 14 }

		
--  1.3.6.1.4.1.37950.1.1.6.1.1.7.17
		-- 1.3.6.1.4.1.37950.1.1.6.1.1.7.17
		gOnuCfgGemportRateLimitTable OBJECT-TYPE
			SYNTAX SEQUENCE OF GOnuCfgGemportRateLimitEntry
			MAX-ACCESS not-accessible
			STATUS current
			DESCRIPTION
				"Description."
			::= { gOnuCfg 17 }

		
--  1.3.6.1.4.1.37950.1.1.6.1.1.7.17.1
		-- 1.3.6.1.4.1.37950.1.1.6.1.1.7.17.1
		gOnuCfgGemportRateLimitEntry OBJECT-TYPE
			SYNTAX GOnuCfgGemportRateLimitEntry
			MAX-ACCESS not-accessible
			STATUS current
			DESCRIPTION
				"Description."
			INDEX { gOnuCfgGemportRateLimitTablePonInx, gOnuCfgGemportRateLimitTableOnuInx, gOnuCfgGemportRateLimitTableGemId, gOnuCfgGemportRateLimitTableTcont }
			::= { gOnuCfgGemportRateLimitTable 1 }

		
		GOnuCfgGemportRateLimitEntry ::=
			SEQUENCE { 
				gOnuCfgGemportRateLimitTablePonInx
					Integer32,
				gOnuCfgGemportRateLimitTableOnuInx
					Integer32,
				gOnuCfgGemportRateLimitTableGemId
					Integer32,
				gOnuCfgGemportRateLimitTableName
					OCTET STRING,
				gOnuCfgGemportRateLimitTableTcont
					Integer32,
				gOnuCfgGemportRateLimitTableUpsCir
					Unsigned32,
				gOnuCfgGemportRateLimitTableUpsPir
					Unsigned32,
				gOnuCfgGemportRateLimitTableDnsCir
					Unsigned32,
				gOnuCfgGemportRateLimitTableDnsPir
					Unsigned32,
				gOnuCfgGemportRateLimitTableAction
					INTEGER
			 }

--  1.3.6.1.4.1.37950.1.1.6.1.1.7.17.1.1
		-- 1.3.6.1.4.1.37950.1.1.6.1.1.7.17.1.1
		gOnuCfgGemportRateLimitTablePonInx OBJECT-TYPE
			SYNTAX Integer32 (1..16)
			MAX-ACCESS read-write
			STATUS current
			DESCRIPTION
				"Description."
			::= { gOnuCfgGemportRateLimitEntry 1 }

		
--  1.3.6.1.4.1.37950.1.1.6.1.1.7.17.1.2
		-- 1.3.6.1.4.1.37950.1.1.6.1.1.7.17.1.2
		gOnuCfgGemportRateLimitTableOnuInx OBJECT-TYPE
			SYNTAX Integer32 (1..128)
			MAX-ACCESS read-write
			STATUS current
			DESCRIPTION
				"Description."
			::= { gOnuCfgGemportRateLimitEntry 2 }

		
--  1.3.6.1.4.1.37950.1.1.6.1.1.7.17.1.3
		-- 1.3.6.1.4.1.37950.1.1.6.1.1.7.17.1.3
		gOnuCfgGemportRateLimitTableGemId OBJECT-TYPE
			SYNTAX Integer32
			MAX-ACCESS read-write
			STATUS current
			DESCRIPTION
				"Description."
			::= { gOnuCfgGemportRateLimitEntry 3 }

		
--  1.3.6.1.4.1.37950.1.1.6.1.1.7.17.1.4
		-- 1.3.6.1.4.1.37950.1.1.6.1.1.7.17.1.4
		gOnuCfgGemportRateLimitTableName OBJECT-TYPE
			SYNTAX OCTET STRING
			MAX-ACCESS read-write
			STATUS current
			DESCRIPTION
				"Description."
			::= { gOnuCfgGemportRateLimitEntry 4 }

		
--  1.3.6.1.4.1.37950.1.1.6.1.1.7.17.1.5
		-- 1.3.6.1.4.1.37950.1.1.6.1.1.7.17.1.5
		gOnuCfgGemportRateLimitTableTcont OBJECT-TYPE
			SYNTAX Integer32
			MAX-ACCESS read-write
			STATUS current
			DESCRIPTION
				"Description."
			::= { gOnuCfgGemportRateLimitEntry 5 }

		
--  1.3.6.1.4.1.37950.1.1.6.1.1.7.17.1.6
		-- 1.3.6.1.4.1.37950.1.1.6.1.1.7.17.1.6
		gOnuCfgGemportRateLimitTableUpsCir OBJECT-TYPE
			SYNTAX Unsigned32 (0..4294967295)
			MAX-ACCESS read-write
			STATUS current
			DESCRIPTION
				"Description."
			::= { gOnuCfgGemportRateLimitEntry 6 }

		
--  1.3.6.1.4.1.37950.1.1.6.1.1.7.17.1.7
		-- 1.3.6.1.4.1.37950.1.1.6.1.1.7.17.1.7
		gOnuCfgGemportRateLimitTableUpsPir OBJECT-TYPE
			SYNTAX Unsigned32 (0..4294967295)
			MAX-ACCESS read-write
			STATUS current
			DESCRIPTION
				"Description."
			::= { gOnuCfgGemportRateLimitEntry 7 }

		
--  1.3.6.1.4.1.37950.1.1.6.1.1.7.17.1.8
		-- 1.3.6.1.4.1.37950.1.1.6.1.1.7.17.1.8
		gOnuCfgGemportRateLimitTableDnsCir OBJECT-TYPE
			SYNTAX Unsigned32 (0..4294967295)
			MAX-ACCESS read-write
			STATUS current
			DESCRIPTION
				"Description."
			::= { gOnuCfgGemportRateLimitEntry 8 }

		
--  1.3.6.1.4.1.37950.1.1.6.1.1.7.17.1.9
		-- 1.3.6.1.4.1.37950.1.1.6.1.1.7.17.1.9
		gOnuCfgGemportRateLimitTableDnsPir OBJECT-TYPE
			SYNTAX Unsigned32 (0..4294967295)
			MAX-ACCESS read-write
			STATUS current
			DESCRIPTION
				"Description."
			::= { gOnuCfgGemportRateLimitEntry 9 }

		
--  1.3.6.1.4.1.37950.1.1.6.1.1.7.17.1.10
		-- 1.3.6.1.4.1.37950.1.1.6.1.1.7.17.1.10
		gOnuCfgGemportRateLimitTableAction OBJECT-TYPE
			SYNTAX INTEGER { delete(1) }
			MAX-ACCESS read-write
			STATUS current
			DESCRIPTION
				"Description."
			::= { gOnuCfgGemportRateLimitEntry 10 }

		
--  1.3.6.1.4.1.37950.1.1.6.1.1.7.18
		-- 1.3.6.1.4.1.37950.1.1.6.1.1.7.18
		gOnuCfgMacLimitTable OBJECT-TYPE
			SYNTAX SEQUENCE OF GOnuCfgMacLimitEntry
			MAX-ACCESS not-accessible
			STATUS current
			DESCRIPTION
				"Description."
			::= { gOnuCfg 18 }

		
--  1.3.6.1.4.1.37950.1.1.6.1.1.7.18.1
		-- 1.3.6.1.4.1.37950.1.1.6.1.1.7.18.1
		gOnuCfgMacLimitEntry OBJECT-TYPE
			SYNTAX GOnuCfgMacLimitEntry
			MAX-ACCESS not-accessible
			STATUS current
			DESCRIPTION
				"Description."
			INDEX { gOnuCfgMacLimitTablePonInx, gOnuCfgMacLimitTableOnuInx }
			::= { gOnuCfgMacLimitTable 1 }

		
		GOnuCfgMacLimitEntry ::=
			SEQUENCE { 
				gOnuCfgMacLimitTablePonInx
					Integer32,
				gOnuCfgMacLimitTableOnuInx
					Integer32,
				gOnuCfgMacLimitTableVal
					Integer32
			 }

--  1.3.6.1.4.1.37950.1.1.6.1.1.7.18.1.1
		-- 1.3.6.1.4.1.37950.1.1.6.1.1.7.18.1.1
		gOnuCfgMacLimitTablePonInx OBJECT-TYPE
			SYNTAX Integer32 (1..16)
			MAX-ACCESS read-write
			STATUS current
			DESCRIPTION
				"Description."
			::= { gOnuCfgMacLimitEntry 1 }

		
--  1.3.6.1.4.1.37950.1.1.6.1.1.7.18.1.2
		-- 1.3.6.1.4.1.37950.1.1.6.1.1.7.18.1.2
		gOnuCfgMacLimitTableOnuInx OBJECT-TYPE
			SYNTAX Integer32 (1..128)
			MAX-ACCESS read-write
			STATUS current
			DESCRIPTION
				"Description."
			::= { gOnuCfgMacLimitEntry 2 }

		
--  1.3.6.1.4.1.37950.1.1.6.1.1.7.18.1.3
		-- 1.3.6.1.4.1.37950.1.1.6.1.1.7.18.1.3
		gOnuCfgMacLimitTableVal OBJECT-TYPE
			SYNTAX Integer32 (0..255)
			MAX-ACCESS read-write
			STATUS current
			DESCRIPTION
				"Description."
			::= { gOnuCfgMacLimitEntry 3 }

		
--  1.3.6.1.4.1.37950.1.1.6.1.1.7.19
		-- 1.3.6.1.4.1.37950.1.1.6.1.1.7.19
		gOnuCfgCATV OBJECT IDENTIFIER ::= { gOnuCfg 19 }

		
--  1.3.6.1.4.1.37950.1.1.6.1.1.7.19.1
		-- 1.3.6.1.4.1.37950.1.1.6.1.1.7.19.1
		gOnuCfgCATVPon OBJECT-TYPE
			SYNTAX Integer32
			MAX-ACCESS read-write
			STATUS current
			DESCRIPTION
				"Description."
			::= { gOnuCfgCATV 1 }

		
--  1.3.6.1.4.1.37950.1.1.6.1.1.7.19.2
		-- 1.3.6.1.4.1.37950.1.1.6.1.1.7.19.2
		gOnuCfgCATVOnu OBJECT-TYPE
			SYNTAX Integer32
			MAX-ACCESS read-write
			STATUS current
			DESCRIPTION
				"Description."
			::= { gOnuCfgCATV 2 }

		
--  1.3.6.1.4.1.37950.1.1.6.1.1.7.19.3
		-- 1.3.6.1.4.1.37950.1.1.6.1.1.7.19.3
		gOnuCfgCATVPortInx OBJECT-TYPE
			SYNTAX Integer32 (0..255)
			MAX-ACCESS read-write
			STATUS current
			DESCRIPTION
				"Description."
			::= { gOnuCfgCATV 3 }

		
--  1.3.6.1.4.1.37950.1.1.6.1.1.7.19.4
		-- 1.3.6.1.4.1.37950.1.1.6.1.1.7.19.4
		gOnuCfgCATVSlotInx OBJECT-TYPE
			SYNTAX Integer32 (0..255)
			MAX-ACCESS read-write
			STATUS current
			DESCRIPTION
				"Description."
			::= { gOnuCfgCATV 4 }

		
--  1.3.6.1.4.1.37950.1.1.6.1.1.7.19.5
		-- 1.3.6.1.4.1.37950.1.1.6.1.1.7.19.5
		gOnuCfgCATVState OBJECT-TYPE
			SYNTAX INTEGER
				{
				unlock(1),
				lock(2)
				}
			MAX-ACCESS read-write
			STATUS current
			DESCRIPTION
				"Description."
			::= { gOnuCfgCATV 5 }

		
--  1.3.6.1.4.1.37950.1.1.6.1.1.7.19.6
		-- 1.3.6.1.4.1.37950.1.1.6.1.1.7.19.6
		gOnuCfgCATVPower OBJECT-TYPE
			SYNTAX INTEGER
				{
				disable(1),
				enable(2)
				}
			MAX-ACCESS read-write
			STATUS current
			DESCRIPTION
				"Description."
			::= { gOnuCfgCATV 6 }

		
--  1.3.6.1.4.1.37950.1.1.6.1.1.7.19.7
		-- 1.3.6.1.4.1.37950.1.1.6.1.1.7.19.7
		gOnuCfgCATVAction OBJECT-TYPE
			SYNTAX INTEGER { commit(1) }
			MAX-ACCESS read-write
			STATUS current
			DESCRIPTION
				"Description."
			::= { gOnuCfgCATV 7 }

		
--  1.3.6.1.4.1.37950.1.1.6.1.1.7.20
		-- 1.3.6.1.4.1.37950.1.1.6.1.1.7.20
		gOnuCfgTr069 OBJECT IDENTIFIER ::= { gOnuCfg 20 }

		
--  1.3.6.1.4.1.37950.1.1.6.1.1.7.20.1
		-- 1.3.6.1.4.1.37950.1.1.6.1.1.7.20.1
		gOnuCfgTr069Pon OBJECT-TYPE
			SYNTAX Integer32 (1..16)
			MAX-ACCESS read-write
			STATUS current
			DESCRIPTION
				"Description."
			::= { gOnuCfgTr069 1 }

		
--  1.3.6.1.4.1.37950.1.1.6.1.1.7.20.2
		-- 1.3.6.1.4.1.37950.1.1.6.1.1.7.20.2
		gOnuCfgTr069Onu OBJECT-TYPE
			SYNTAX Integer32 (1..128)
			MAX-ACCESS read-write
			STATUS current
			DESCRIPTION
				"Description."
			::= { gOnuCfgTr069 2 }

		
--  1.3.6.1.4.1.37950.1.1.6.1.1.7.20.3
		-- 1.3.6.1.4.1.37950.1.1.6.1.1.7.20.3
		gOnuCfgTr069Veipid OBJECT-TYPE
			SYNTAX Integer32 (1..8)
			MAX-ACCESS read-write
			STATUS current
			DESCRIPTION
				"Description."
			::= { gOnuCfgTr069 3 }

		
--  1.3.6.1.4.1.37950.1.1.6.1.1.7.20.4
		-- 1.3.6.1.4.1.37950.1.1.6.1.1.7.20.4
		gOnuCfgTr069State OBJECT-TYPE
			SYNTAX INTEGER
				{
				lock(0),
				unlock(1)
				}
			MAX-ACCESS read-write
			STATUS current
			DESCRIPTION
				"Description."
			::= { gOnuCfgTr069 4 }

		
--  1.3.6.1.4.1.37950.1.1.6.1.1.7.20.5
		-- 1.3.6.1.4.1.37950.1.1.6.1.1.7.20.5
		gOnuCfgTr069Address OBJECT-TYPE
			SYNTAX OCTET STRING
			MAX-ACCESS read-write
			STATUS current
			DESCRIPTION
				"Description."
			::= { gOnuCfgTr069 5 }

		
--  1.3.6.1.4.1.37950.1.1.6.1.1.7.20.6
		-- 1.3.6.1.4.1.37950.1.1.6.1.1.7.20.6
		gOnuCfgTr069Username OBJECT-TYPE
			SYNTAX OCTET STRING
			MAX-ACCESS read-write
			STATUS current
			DESCRIPTION
				"Description."
			::= { gOnuCfgTr069 6 }

		
--  1.3.6.1.4.1.37950.1.1.6.1.1.7.20.7
		-- 1.3.6.1.4.1.37950.1.1.6.1.1.7.20.7
		gOnuCfgTr069Password OBJECT-TYPE
			SYNTAX OCTET STRING
			MAX-ACCESS read-write
			STATUS current
			DESCRIPTION
				"Description."
			::= { gOnuCfgTr069 7 }

		
--  1.3.6.1.4.1.37950.1.1.6.1.1.7.20.8
		-- 1.3.6.1.4.1.37950.1.1.6.1.1.7.20.8
		gOnuCfgTr069Tag OBJECT-TYPE
			SYNTAX INTEGER
				{
				disable(0),
				enable(1)
				}
			MAX-ACCESS read-write
			STATUS current
			DESCRIPTION
				"Description."
			::= { gOnuCfgTr069 8 }

		
--  1.3.6.1.4.1.37950.1.1.6.1.1.7.20.9
		-- 1.3.6.1.4.1.37950.1.1.6.1.1.7.20.9
		gOnuCfgTr069Vlanid OBJECT-TYPE
			SYNTAX Integer32 (1..4094)
			MAX-ACCESS read-write
			STATUS current
			DESCRIPTION
				"Description."
			::= { gOnuCfgTr069 9 }

		
--  1.3.6.1.4.1.37950.1.1.6.1.1.7.20.10
		-- 1.3.6.1.4.1.37950.1.1.6.1.1.7.20.10
		gOnuCfgTr069Priority OBJECT-TYPE
			SYNTAX Integer32 (0..7)
			MAX-ACCESS read-write
			STATUS current
			DESCRIPTION
				"Description."
			::= { gOnuCfgTr069 10 }

		
--  1.3.6.1.4.1.37950.1.1.6.1.1.7.20.11
		-- 1.3.6.1.4.1.37950.1.1.6.1.1.7.20.11
		gOnuCfgTr069Action OBJECT-TYPE
			SYNTAX INTEGER { commit(1) }
			MAX-ACCESS read-write
			STATUS current
			DESCRIPTION
				"Description."
			::= { gOnuCfgTr069 11 }

		
--  1.3.6.1.4.1.37950.1.1.6.1.1.7.21
		-- 1.3.6.1.4.1.37950.1.1.6.1.1.7.21
		gOnuCfgFec OBJECT IDENTIFIER ::= { gOnuCfg 21 }

		
--  1.3.6.1.4.1.37950.1.1.6.1.1.7.21.1
		-- 1.3.6.1.4.1.37950.1.1.6.1.1.7.21.1
		gOnuCfgFecPon OBJECT-TYPE
			SYNTAX Integer32 (1..16)
			MAX-ACCESS read-write
			STATUS current
			DESCRIPTION
				"Description."
			::= { gOnuCfgFec 1 }

		
--  1.3.6.1.4.1.37950.1.1.6.1.1.7.21.2
		-- 1.3.6.1.4.1.37950.1.1.6.1.1.7.21.2
		gOnuCfgFecOnu OBJECT-TYPE
			SYNTAX Integer32 (1..128)
			MAX-ACCESS read-write
			STATUS current
			DESCRIPTION
				"Description."
			::= { gOnuCfgFec 2 }

		
--  1.3.6.1.4.1.37950.1.1.6.1.1.7.21.3
		-- 1.3.6.1.4.1.37950.1.1.6.1.1.7.21.3
		gOnuCfgFecState OBJECT-TYPE
			SYNTAX INTEGER
				{
				disable(0),
				enable(1)
				}
			MAX-ACCESS read-write
			STATUS current
			DESCRIPTION
				"Description."
			::= { gOnuCfgFec 3 }

		
--   1.3.6.1.4.1.37950.1.1.6.1.1.7.21
-- 1.3.6.1.4.1.37950.1.1.6.1.1.7.22
		-- 1.3.6.1.4.1.37950.1.1.6.1.1.7.22
		gOnuCfgIphostVlanConfig OBJECT IDENTIFIER ::= { gOnuCfg 22 }

		
--   1.3.6.1.4.1.37950.1.1.6.1.1.7.21.1
-- 1.3.6.1.4.1.37950.1.1.6.1.1.7.22.1
		-- 1.3.6.1.4.1.37950.1.1.6.1.1.7.22.1
		gOnuCfgIphostVlanConfigSlotInx OBJECT-TYPE
			SYNTAX Integer32 (0..4)
			MAX-ACCESS read-write
			STATUS current
			DESCRIPTION
				"Description."
			::= { gOnuCfgIphostVlanConfig 1 }

		
--   1.3.6.1.4.1.37950.1.1.6.1.1.7.21.2
-- 1.3.6.1.4.1.37950.1.1.6.1.1.7.22.2
		-- 1.3.6.1.4.1.37950.1.1.6.1.1.7.22.2
		gOnuCfgIphostVlanConfigPonInx OBJECT-TYPE
			SYNTAX Integer32 (1..16)
			MAX-ACCESS read-write
			STATUS current
			DESCRIPTION
				"Description."
			::= { gOnuCfgIphostVlanConfig 2 }

		
--   1.3.6.1.4.1.37950.1.1.6.1.1.7.21.3
-- 1.3.6.1.4.1.37950.1.1.6.1.1.7.22.3
		-- 1.3.6.1.4.1.37950.1.1.6.1.1.7.22.3
		gOnuCfgIphostVlanConfigOnuInx OBJECT-TYPE
			SYNTAX Integer32 (1..256)
			MAX-ACCESS read-write
			STATUS current
			DESCRIPTION
				"Description."
			::= { gOnuCfgIphostVlanConfig 3 }

		
--   1.3.6.1.4.1.37950.1.1.6.1.1.7.21.4
-- 1.3.6.1.4.1.37950.1.1.6.1.1.7.22.4
		-- 1.3.6.1.4.1.37950.1.1.6.1.1.7.22.4
		gOnuCfgIphostVlanConfigVlan OBJECT-TYPE
			SYNTAX Integer32 (1..4094)
			MAX-ACCESS read-write
			STATUS current
			DESCRIPTION
				"Description."
			::= { gOnuCfgIphostVlanConfig 4 }

		
--   1.3.6.1.4.1.37950.1.1.6.1.1.7.21.5
-- 1.3.6.1.4.1.37950.1.1.6.1.1.7.22.5
		-- 1.3.6.1.4.1.37950.1.1.6.1.1.7.22.5
		gOnuCfgIphostVlanConfigVlanPri OBJECT-TYPE
			SYNTAX Integer32 (1..15)
			MAX-ACCESS read-write
			STATUS current
			DESCRIPTION
				"Description."
			::= { gOnuCfgIphostVlanConfig 5 }

		
--   1.3.6.1.4.1.37950.1.1.6.1.1.7.21.6
-- 1.3.6.1.4.1.37950.1.1.6.1.1.7.22.6
		-- 1.3.6.1.4.1.37950.1.1.6.1.1.7.22.6
		gOnuCfgIphostVlanConfigAction OBJECT-TYPE
			SYNTAX INTEGER
				{
				delete(0),
				commit(1)
				}
			MAX-ACCESS read-write
			STATUS current
			DESCRIPTION
				"Description."
			::= { gOnuCfgIphostVlanConfig 6 }

		
		-- 1.3.6.1.4.1.37950.1.1.6.1.1.7.22.7
		gOnuCfgIphostVlanConfigIphostId OBJECT-TYPE
			SYNTAX Integer32
			MAX-ACCESS read-write
			STATUS current
			DESCRIPTION
				"Description."
			::= { gOnuCfgIphostVlanConfig 7 }

		
--  1.3.6.1.4.1.37950.1.1.6.1.1.8
		-- 1.3.6.1.4.1.37950.1.1.6.1.1.8
		gOnuSrvInfo OBJECT IDENTIFIER ::= { gOnuAuthList 8 }

		
--  1.3.6.1.4.1.37950.1.1.6.1.1.8.1
		-- 1.3.6.1.4.1.37950.1.1.6.1.1.8.1
		gOnuSrvInfoTcontTable OBJECT-TYPE
			SYNTAX SEQUENCE OF GOnuSrvInfoTcontEntry
			MAX-ACCESS not-accessible
			STATUS current
			DESCRIPTION
				"Description."
			::= { gOnuSrvInfo 1 }

		
--  1.3.6.1.4.1.37950.1.1.6.1.1.8.1.1
		-- 1.3.6.1.4.1.37950.1.1.6.1.1.8.1.1
		gOnuSrvInfoTcontEntry OBJECT-TYPE
			SYNTAX GOnuSrvInfoTcontEntry
			MAX-ACCESS not-accessible
			STATUS current
			DESCRIPTION
				"Description."
			INDEX { gOnuSrvInfoTcontPonInx, gOnuSrvInfoTcontOnuInx, gOnuSrvInfoTcontId }
			::= { gOnuSrvInfoTcontTable 1 }

		
		GOnuSrvInfoTcontEntry ::=
			SEQUENCE { 
				gOnuSrvInfoTcontPonInx
					Integer32,
				gOnuSrvInfoTcontOnuInx
					Integer32,
				gOnuSrvInfoTcontId
					Integer32,
				gOnuSrvInfoTcontName
					OCTET STRING,
				gOnuSrvInfoTcontDbaName
					OCTET STRING
			 }

--  1.3.6.1.4.1.37950.1.1.6.1.1.8.1.1.1
		-- 1.3.6.1.4.1.37950.1.1.6.1.1.8.1.1.1
		gOnuSrvInfoTcontPonInx OBJECT-TYPE
			SYNTAX Integer32 (1..16)
			MAX-ACCESS read-only
			STATUS current
			DESCRIPTION
				"Description."
			::= { gOnuSrvInfoTcontEntry 1 }

		
--  1.3.6.1.4.1.37950.1.1.6.1.1.8.1.1.2
		-- 1.3.6.1.4.1.37950.1.1.6.1.1.8.1.1.2
		gOnuSrvInfoTcontOnuInx OBJECT-TYPE
			SYNTAX Integer32 (1..128)
			MAX-ACCESS read-only
			STATUS current
			DESCRIPTION
				"Description."
			::= { gOnuSrvInfoTcontEntry 2 }

		
--  1.3.6.1.4.1.37950.1.1.6.1.1.8.1.1.3
		-- 1.3.6.1.4.1.37950.1.1.6.1.1.8.1.1.3
		gOnuSrvInfoTcontId OBJECT-TYPE
			SYNTAX Integer32 (1..255)
			MAX-ACCESS read-only
			STATUS current
			DESCRIPTION
				"Description."
			::= { gOnuSrvInfoTcontEntry 3 }

		
--  1.3.6.1.4.1.37950.1.1.6.1.1.8.1.1.4
		-- 1.3.6.1.4.1.37950.1.1.6.1.1.8.1.1.4
		gOnuSrvInfoTcontName OBJECT-TYPE
			SYNTAX OCTET STRING
			MAX-ACCESS read-only
			STATUS current
			DESCRIPTION
				"Description."
			::= { gOnuSrvInfoTcontEntry 4 }

		
--  1.3.6.1.4.1.37950.1.1.6.1.1.8.1.1.5
		-- 1.3.6.1.4.1.37950.1.1.6.1.1.8.1.1.5
		gOnuSrvInfoTcontDbaName OBJECT-TYPE
			SYNTAX OCTET STRING
			MAX-ACCESS read-only
			STATUS current
			DESCRIPTION
				"Description."
			::= { gOnuSrvInfoTcontEntry 5 }

		
--  1.3.6.1.4.1.37950.1.1.6.1.1.8.2
		-- 1.3.6.1.4.1.37950.1.1.6.1.1.8.2
		gOnuSrvInfoTaTable OBJECT-TYPE
			SYNTAX SEQUENCE OF GOnuSrvInfoTaEntry
			MAX-ACCESS not-accessible
			STATUS current
			DESCRIPTION
				"Description."
			::= { gOnuSrvInfo 2 }

		
--  1.3.6.1.4.1.37950.1.1.6.1.1.8.2.1
		-- 1.3.6.1.4.1.37950.1.1.6.1.1.8.2.1
		gOnuSrvInfoTaEntry OBJECT-TYPE
			SYNTAX GOnuSrvInfoTaEntry
			MAX-ACCESS not-accessible
			STATUS current
			DESCRIPTION
				"Description."
			INDEX { gOnuSrvInfoTa }
			::= { gOnuSrvInfoTaTable 1 }

		
		GOnuSrvInfoTaEntry ::=
			SEQUENCE { 
				gOnuSrvInfoTa
					OCTET STRING
			 }

--  1.3.6.1.4.1.37950.1.1.6.1.1.8.2.1.1
		-- 1.3.6.1.4.1.37950.1.1.6.1.1.8.2.1.1
		gOnuSrvInfoTa OBJECT-TYPE
			SYNTAX OCTET STRING
			MAX-ACCESS read-only
			STATUS current
			DESCRIPTION
				"Description."
			::= { gOnuSrvInfoTaEntry 1 }

		
--  1.3.6.1.4.1.37950.1.1.6.1.1.8.3
		-- 1.3.6.1.4.1.37950.1.1.6.1.1.8.3
		gOnuSrvInfoGemTable OBJECT-TYPE
			SYNTAX SEQUENCE OF GOnuSrvInfoGemEntry
			MAX-ACCESS not-accessible
			STATUS current
			DESCRIPTION
				"Description."
			::= { gOnuSrvInfo 3 }

		
--  1.3.6.1.4.1.37950.1.1.6.1.1.8.3.1
		-- 1.3.6.1.4.1.37950.1.1.6.1.1.8.3.1
		gOnuSrvInfoGemEntry OBJECT-TYPE
			SYNTAX GOnuSrvInfoGemEntry
			MAX-ACCESS not-accessible
			STATUS current
			DESCRIPTION
				"Description."
			INDEX { gOnuSrvInfoGemPonInx, gOnuSrvInfoGemOnuInx, gOnuSrvInfoGemId }
			::= { gOnuSrvInfoGemTable 1 }

		
		GOnuSrvInfoGemEntry ::=
			SEQUENCE { 
				gOnuSrvInfoGemPonInx
					Integer32,
				gOnuSrvInfoGemOnuInx
					Integer32,
				gOnuSrvInfoGemId
					Integer32,
				gOnuSrvInfoGemName
					OCTET STRING,
				gOnuSrvInfoGemTcontId
					Integer32,
				gOnuSrvInfoGemCos
					Integer32,
				gOnuSrvInfoGemUpTraffic
					OCTET STRING,
				gOnuSrvInfoGemDnTraffic
					OCTET STRING,
				gOnuSrvInfoGemUpQId
					Integer32,
				gOnuSrvInfoGemDnQId
					Integer32,
				gOnuSrvInfoGemState
					INTEGER
			 }

--  1.3.6.1.4.1.37950.1.1.6.1.1.8.3.1.1
		-- 1.3.6.1.4.1.37950.1.1.6.1.1.8.3.1.1
		gOnuSrvInfoGemPonInx OBJECT-TYPE
			SYNTAX Integer32 (1..16)
			MAX-ACCESS read-only
			STATUS current
			DESCRIPTION
				"Description."
			::= { gOnuSrvInfoGemEntry 1 }

		
--  1.3.6.1.4.1.37950.1.1.6.1.1.8.3.1.2
		-- 1.3.6.1.4.1.37950.1.1.6.1.1.8.3.1.2
		gOnuSrvInfoGemOnuInx OBJECT-TYPE
			SYNTAX Integer32 (1..128)
			MAX-ACCESS read-only
			STATUS current
			DESCRIPTION
				"Description."
			::= { gOnuSrvInfoGemEntry 2 }

		
--  1.3.6.1.4.1.37950.1.1.6.1.1.8.3.1.3
		-- 1.3.6.1.4.1.37950.1.1.6.1.1.8.3.1.3
		gOnuSrvInfoGemId OBJECT-TYPE
			SYNTAX Integer32 (1..255)
			MAX-ACCESS read-only
			STATUS current
			DESCRIPTION
				"Description."
			::= { gOnuSrvInfoGemEntry 3 }

		
--  1.3.6.1.4.1.37950.1.1.6.1.1.8.3.1.4
		-- 1.3.6.1.4.1.37950.1.1.6.1.1.8.3.1.4
		gOnuSrvInfoGemName OBJECT-TYPE
			SYNTAX OCTET STRING
			MAX-ACCESS read-only
			STATUS current
			DESCRIPTION
				"Description."
			::= { gOnuSrvInfoGemEntry 4 }

		
--  1.3.6.1.4.1.37950.1.1.6.1.1.8.3.1.5
		-- 1.3.6.1.4.1.37950.1.1.6.1.1.8.3.1.5
		gOnuSrvInfoGemTcontId OBJECT-TYPE
			SYNTAX Integer32 (1..255)
			MAX-ACCESS read-only
			STATUS current
			DESCRIPTION
				"Description."
			::= { gOnuSrvInfoGemEntry 5 }

		
--  1.3.6.1.4.1.37950.1.1.6.1.1.8.3.1.6
		-- 1.3.6.1.4.1.37950.1.1.6.1.1.8.3.1.6
		gOnuSrvInfoGemCos OBJECT-TYPE
			SYNTAX Integer32 (0..8)
			MAX-ACCESS read-only
			STATUS current
			DESCRIPTION
				"Description."
			::= { gOnuSrvInfoGemEntry 6 }

		
--  1.3.6.1.4.1.37950.1.1.6.1.1.8.3.1.7
		-- 1.3.6.1.4.1.37950.1.1.6.1.1.8.3.1.7
		gOnuSrvInfoGemUpTraffic OBJECT-TYPE
			SYNTAX OCTET STRING
			MAX-ACCESS read-only
			STATUS current
			DESCRIPTION
				"Description."
			::= { gOnuSrvInfoGemEntry 7 }

		
--  1.3.6.1.4.1.37950.1.1.6.1.1.8.3.1.8
		-- 1.3.6.1.4.1.37950.1.1.6.1.1.8.3.1.8
		gOnuSrvInfoGemDnTraffic OBJECT-TYPE
			SYNTAX OCTET STRING
			MAX-ACCESS read-only
			STATUS current
			DESCRIPTION
				"Description."
			::= { gOnuSrvInfoGemEntry 8 }

		
--  1.3.6.1.4.1.37950.1.1.6.1.1.8.3.1.9
		-- 1.3.6.1.4.1.37950.1.1.6.1.1.8.3.1.9
		gOnuSrvInfoGemUpQId OBJECT-TYPE
			SYNTAX Integer32 (0..4)
			MAX-ACCESS read-only
			STATUS current
			DESCRIPTION
				"Description."
			::= { gOnuSrvInfoGemEntry 9 }

		
--  1.3.6.1.4.1.37950.1.1.6.1.1.8.3.1.10
		-- 1.3.6.1.4.1.37950.1.1.6.1.1.8.3.1.10
		gOnuSrvInfoGemDnQId OBJECT-TYPE
			SYNTAX Integer32 (0..8)
			MAX-ACCESS read-only
			STATUS current
			DESCRIPTION
				"Description."
			::= { gOnuSrvInfoGemEntry 10 }

		
--  1.3.6.1.4.1.37950.1.1.6.1.1.8.3.1.11
		-- 1.3.6.1.4.1.37950.1.1.6.1.1.8.3.1.11
		gOnuSrvInfoGemState OBJECT-TYPE
			SYNTAX INTEGER (0..1)
			MAX-ACCESS read-only
			STATUS current
			DESCRIPTION
				"Description."
			::= { gOnuSrvInfoGemEntry 11 }

		
--  1.3.6.1.4.1.37950.1.1.6.1.1.8.4
		-- 1.3.6.1.4.1.37950.1.1.6.1.1.8.4
		gOnuSrvInfoTbTable OBJECT-TYPE
			SYNTAX SEQUENCE OF GOnuSrvInfoTbEntry
			MAX-ACCESS not-accessible
			STATUS current
			DESCRIPTION
				"Description."
			::= { gOnuSrvInfo 4 }

		
--  1.3.6.1.4.1.37950.1.1.6.1.1.8.4.1
		-- 1.3.6.1.4.1.37950.1.1.6.1.1.8.4.1
		gOnuSrvInfoTbEntry OBJECT-TYPE
			SYNTAX GOnuSrvInfoTbEntry
			MAX-ACCESS not-accessible
			STATUS current
			DESCRIPTION
				"Description."
			INDEX { gOnuSrvInfoTb }
			::= { gOnuSrvInfoTbTable 1 }

		
		GOnuSrvInfoTbEntry ::=
			SEQUENCE { 
				gOnuSrvInfoTb
					OCTET STRING
			 }

--  1.3.6.1.4.1.37950.1.1.6.1.1.8.4.1.1
		-- 1.3.6.1.4.1.37950.1.1.6.1.1.8.4.1.1
		gOnuSrvInfoTb OBJECT-TYPE
			SYNTAX OCTET STRING
			MAX-ACCESS read-only
			STATUS current
			DESCRIPTION
				"Description."
			::= { gOnuSrvInfoTbEntry 1 }

		
--  1.3.6.1.4.1.37950.1.1.6.1.1.8.5
		-- 1.3.6.1.4.1.37950.1.1.6.1.1.8.5
		gOnuSrvInfoSrvTable OBJECT-TYPE
			SYNTAX SEQUENCE OF GOnuSrvInfoSrvEntry
			MAX-ACCESS not-accessible
			STATUS current
			DESCRIPTION
				"Description."
			::= { gOnuSrvInfo 5 }

		
--  1.3.6.1.4.1.37950.1.1.6.1.1.8.5.1
		-- 1.3.6.1.4.1.37950.1.1.6.1.1.8.5.1
		gOnuSrvInfoSrvEntry OBJECT-TYPE
			SYNTAX GOnuSrvInfoSrvEntry
			MAX-ACCESS not-accessible
			STATUS current
			DESCRIPTION
				"Description."
			INDEX { gOnuSrvInfoSrvPonInx, gOnuSrvInfoSrvOnuInx, gOnuSrvInfoSrvName }
			::= { gOnuSrvInfoSrvTable 1 }

		
		GOnuSrvInfoSrvEntry ::=
			SEQUENCE { 
				gOnuSrvInfoSrvPonInx
					Integer32,
				gOnuSrvInfoSrvOnuInx
					Integer32,
				gOnuSrvInfoSrvName
					OCTET STRING,
				gOnuSrvInfoSrvGemId
					Integer32,
				gOnuSrvInfoSrvVlanMode
					Integer32,
				gOnuSrvInfoSrvVlanList
					OCTET STRING,
				gOnuSrvInfoSrvCosList
					OCTET STRING,
				gOnuSrvInfoSrvPort
					OCTET STRING
			 }

--  1.3.6.1.4.1.37950.1.1.6.1.1.8.5.1.1
		-- 1.3.6.1.4.1.37950.1.1.6.1.1.8.5.1.1
		gOnuSrvInfoSrvPonInx OBJECT-TYPE
			SYNTAX Integer32 (1..16)
			MAX-ACCESS read-only
			STATUS current
			DESCRIPTION
				"Description."
			::= { gOnuSrvInfoSrvEntry 1 }

		
--  1.3.6.1.4.1.37950.1.1.6.1.1.8.5.1.2
		-- 1.3.6.1.4.1.37950.1.1.6.1.1.8.5.1.2
		gOnuSrvInfoSrvOnuInx OBJECT-TYPE
			SYNTAX Integer32 (1..128)
			MAX-ACCESS read-only
			STATUS current
			DESCRIPTION
				"Description."
			::= { gOnuSrvInfoSrvEntry 2 }

		
--  1.3.6.1.4.1.37950.1.1.6.1.1.8.5.1.3
		-- 1.3.6.1.4.1.37950.1.1.6.1.1.8.5.1.3
		gOnuSrvInfoSrvName OBJECT-TYPE
			SYNTAX OCTET STRING
			MAX-ACCESS read-only
			STATUS current
			DESCRIPTION
				"Description."
			::= { gOnuSrvInfoSrvEntry 3 }

		
--  1.3.6.1.4.1.37950.1.1.6.1.1.8.5.1.4
		-- 1.3.6.1.4.1.37950.1.1.6.1.1.8.5.1.4
		gOnuSrvInfoSrvGemId OBJECT-TYPE
			SYNTAX Integer32 (1..255)
			MAX-ACCESS read-only
			STATUS current
			DESCRIPTION
				"Description."
			::= { gOnuSrvInfoSrvEntry 4 }

		
--  1.3.6.1.4.1.37950.1.1.6.1.1.8.5.1.5
		-- 1.3.6.1.4.1.37950.1.1.6.1.1.8.5.1.5
		gOnuSrvInfoSrvVlanMode OBJECT-TYPE
			SYNTAX Integer32 (0..2)
			MAX-ACCESS read-only
			STATUS current
			DESCRIPTION
				"Description."
			::= { gOnuSrvInfoSrvEntry 5 }

		
--  1.3.6.1.4.1.37950.1.1.6.1.1.8.5.1.6
		-- 1.3.6.1.4.1.37950.1.1.6.1.1.8.5.1.6
		gOnuSrvInfoSrvVlanList OBJECT-TYPE
			SYNTAX OCTET STRING
			MAX-ACCESS read-only
			STATUS current
			DESCRIPTION
				"Description."
			::= { gOnuSrvInfoSrvEntry 6 }

		
--  1.3.6.1.4.1.37950.1.1.6.1.1.8.5.1.7
		-- 1.3.6.1.4.1.37950.1.1.6.1.1.8.5.1.7
		gOnuSrvInfoSrvCosList OBJECT-TYPE
			SYNTAX OCTET STRING
			MAX-ACCESS read-write
			STATUS current
			DESCRIPTION
				"Description."
			::= { gOnuSrvInfoSrvEntry 7 }

		
--  1.3.6.1.4.1.37950.1.1.6.1.1.8.5.1.8
		-- 1.3.6.1.4.1.37950.1.1.6.1.1.8.5.1.8
		gOnuSrvInfoSrvPort OBJECT-TYPE
			SYNTAX OCTET STRING
			MAX-ACCESS read-write
			STATUS current
			DESCRIPTION
				"Description."
			::= { gOnuSrvInfoSrvEntry 8 }

		
--  1.3.6.1.4.1.37950.1.1.6.1.1.8.6
		-- 1.3.6.1.4.1.37950.1.1.6.1.1.8.6
		gOnuSrvInfoTcTable OBJECT-TYPE
			SYNTAX SEQUENCE OF GOnuSrvInfoTcEntry
			MAX-ACCESS not-accessible
			STATUS current
			DESCRIPTION
				"Description."
			::= { gOnuSrvInfo 6 }

		
--  1.3.6.1.4.1.37950.1.1.6.1.1.8.6.1
		-- 1.3.6.1.4.1.37950.1.1.6.1.1.8.6.1
		gOnuSrvInfoTcEntry OBJECT-TYPE
			SYNTAX GOnuSrvInfoTcEntry
			MAX-ACCESS not-accessible
			STATUS current
			DESCRIPTION
				"Description."
			INDEX { gOnuSrvInfoTc }
			::= { gOnuSrvInfoTcTable 1 }

		
		GOnuSrvInfoTcEntry ::=
			SEQUENCE { 
				gOnuSrvInfoTc
					OCTET STRING
			 }

--  1.3.6.1.4.1.37950.1.1.6.1.1.8.6.1.1
		-- 1.3.6.1.4.1.37950.1.1.6.1.1.8.6.1.1
		gOnuSrvInfoTc OBJECT-TYPE
			SYNTAX OCTET STRING
			MAX-ACCESS read-only
			STATUS current
			DESCRIPTION
				"Description."
			::= { gOnuSrvInfoTcEntry 1 }

		
--  1.3.6.1.4.1.37950.1.1.6.1.1.8.7
		-- 1.3.6.1.4.1.37950.1.1.6.1.1.8.7
		gOnuSrvInfoSrvPortTable OBJECT-TYPE
			SYNTAX SEQUENCE OF GOnuSrvInfoSrvPortEntry
			MAX-ACCESS not-accessible
			STATUS current
			DESCRIPTION
				"Description."
			::= { gOnuSrvInfo 7 }

		
--  1.3.6.1.4.1.37950.1.1.6.1.1.8.7.1
		-- 1.3.6.1.4.1.37950.1.1.6.1.1.8.7.1
		gOnuSrvInfoSrvPortEntry OBJECT-TYPE
			SYNTAX GOnuSrvInfoSrvPortEntry
			MAX-ACCESS not-accessible
			STATUS current
			DESCRIPTION
				"Description."
			INDEX { gOnuSrvInfoSrvPortPonInx, gOnuSrvInfoSrvPortOnuInx, gOnuSrvInfoSrvPortId }
			::= { gOnuSrvInfoSrvPortTable 1 }

		
		GOnuSrvInfoSrvPortEntry ::=
			SEQUENCE { 
				gOnuSrvInfoSrvPortPonInx
					Integer32,
				gOnuSrvInfoSrvPortOnuInx
					Integer32,
				gOnuSrvInfoSrvPortId
					Integer32,
				gOnuSrvInfoSrvPortGemId
					Integer32,
				gOnuSrvInfoSrvPortSetMode
					Integer32,
				gOnuSrvInfoSrvPortDesc
					OCTET STRING,
				gOnuSrvInfoSrvPortBVid
					Integer32,
				gOnuSrvInfoSrvPortEVid
					Integer32,
				gOnuSrvInfoSrvPortUserInnerVlan
					Integer32,
				gOnuSrvInfoSrvPortUserOuterVlan
					Integer32,
				gOnuSrvInfoSrvPortUPri
					Integer32,
				gOnuSrvInfoSrvPortEType
					OCTET STRING,
				gOnuSrvInfoSrvPortState
					OCTET STRING,
				gOnuSrvInfoSrvPortVid
					Integer32,
				gOnuSrvInfoSrvPortCos
					Integer32,
				gOnuSrvInfoSrvPortSVid
					Integer32,
				gOnuSrvInfoSrvPortSCos
					Integer32
			 }

--  1.3.6.1.4.1.37950.1.1.6.1.1.8.7.1.1
		-- 1.3.6.1.4.1.37950.1.1.6.1.1.8.7.1.1
		gOnuSrvInfoSrvPortPonInx OBJECT-TYPE
			SYNTAX Integer32 (1..16)
			MAX-ACCESS read-only
			STATUS current
			DESCRIPTION
				"Description."
			::= { gOnuSrvInfoSrvPortEntry 1 }

		
--  1.3.6.1.4.1.37950.1.1.6.1.1.8.7.1.2
		-- 1.3.6.1.4.1.37950.1.1.6.1.1.8.7.1.2
		gOnuSrvInfoSrvPortOnuInx OBJECT-TYPE
			SYNTAX Integer32 (1..128)
			MAX-ACCESS read-only
			STATUS current
			DESCRIPTION
				"Description."
			::= { gOnuSrvInfoSrvPortEntry 2 }

		
--  1.3.6.1.4.1.37950.1.1.6.1.1.8.7.1.3
		-- 1.3.6.1.4.1.37950.1.1.6.1.1.8.7.1.3
		gOnuSrvInfoSrvPortId OBJECT-TYPE
			SYNTAX Integer32 (1..128)
			MAX-ACCESS read-only
			STATUS current
			DESCRIPTION
				"Description."
			::= { gOnuSrvInfoSrvPortEntry 3 }

		
--  1.3.6.1.4.1.37950.1.1.6.1.1.8.7.1.4
		-- 1.3.6.1.4.1.37950.1.1.6.1.1.8.7.1.4
		gOnuSrvInfoSrvPortGemId OBJECT-TYPE
			SYNTAX Integer32 (1..128)
			MAX-ACCESS read-only
			STATUS current
			DESCRIPTION
				"Description."
			::= { gOnuSrvInfoSrvPortEntry 4 }

		
--  1.3.6.1.4.1.37950.1.1.6.1.1.8.7.1.5
		-- 1.3.6.1.4.1.37950.1.1.6.1.1.8.7.1.5
		gOnuSrvInfoSrvPortSetMode OBJECT-TYPE
			SYNTAX Integer32 (1..8)
			MAX-ACCESS read-only
			STATUS current
			DESCRIPTION
				"Description."
			::= { gOnuSrvInfoSrvPortEntry 5 }

		
--  1.3.6.1.4.1.37950.1.1.6.1.1.8.7.1.6
		-- 1.3.6.1.4.1.37950.1.1.6.1.1.8.7.1.6
		gOnuSrvInfoSrvPortDesc OBJECT-TYPE
			SYNTAX OCTET STRING
			MAX-ACCESS read-only
			STATUS current
			DESCRIPTION
				"Description."
			::= { gOnuSrvInfoSrvPortEntry 6 }

		
--  1.3.6.1.4.1.37950.1.1.6.1.1.8.7.1.7
		-- 1.3.6.1.4.1.37950.1.1.6.1.1.8.7.1.7
		gOnuSrvInfoSrvPortBVid OBJECT-TYPE
			SYNTAX Integer32 (0..4094)
			MAX-ACCESS read-only
			STATUS current
			DESCRIPTION
				"Description."
			::= { gOnuSrvInfoSrvPortEntry 7 }

		
--  1.3.6.1.4.1.37950.1.1.6.1.1.8.7.1.8
		-- 1.3.6.1.4.1.37950.1.1.6.1.1.8.7.1.8
		gOnuSrvInfoSrvPortEVid OBJECT-TYPE
			SYNTAX Integer32 (0..4094)
			MAX-ACCESS read-only
			STATUS current
			DESCRIPTION
				"Description."
			::= { gOnuSrvInfoSrvPortEntry 8 }

		
--  1.3.6.1.4.1.37950.1.1.6.1.1.8.7.1.9
		-- 1.3.6.1.4.1.37950.1.1.6.1.1.8.7.1.9
		gOnuSrvInfoSrvPortUserInnerVlan OBJECT-TYPE
			SYNTAX Integer32 (0..4094)
			MAX-ACCESS read-only
			STATUS current
			DESCRIPTION
				"Description."
			::= { gOnuSrvInfoSrvPortEntry 9 }

		
--  1.3.6.1.4.1.37950.1.1.6.1.1.8.7.1.10
		-- 1.3.6.1.4.1.37950.1.1.6.1.1.8.7.1.10
		gOnuSrvInfoSrvPortUserOuterVlan OBJECT-TYPE
			SYNTAX Integer32 (0..4094)
			MAX-ACCESS read-only
			STATUS current
			DESCRIPTION
				"Description."
			::= { gOnuSrvInfoSrvPortEntry 10 }

		
--  1.3.6.1.4.1.37950.1.1.6.1.1.8.7.1.11
		-- 1.3.6.1.4.1.37950.1.1.6.1.1.8.7.1.11
		gOnuSrvInfoSrvPortUPri OBJECT-TYPE
			SYNTAX Integer32 (0..7)
			MAX-ACCESS read-only
			STATUS current
			DESCRIPTION
				"Description."
			::= { gOnuSrvInfoSrvPortEntry 11 }

		
--  1.3.6.1.4.1.37950.1.1.6.1.1.8.7.1.12
		-- 1.3.6.1.4.1.37950.1.1.6.1.1.8.7.1.12
		gOnuSrvInfoSrvPortEType OBJECT-TYPE
			SYNTAX OCTET STRING
			MAX-ACCESS read-only
			STATUS current
			DESCRIPTION
				"Description."
			::= { gOnuSrvInfoSrvPortEntry 12 }

		
--  1.3.6.1.4.1.37950.1.1.6.1.1.8.7.1.13
		-- 1.3.6.1.4.1.37950.1.1.6.1.1.8.7.1.13
		gOnuSrvInfoSrvPortState OBJECT-TYPE
			SYNTAX OCTET STRING
			MAX-ACCESS read-only
			STATUS current
			DESCRIPTION
				"Description."
			::= { gOnuSrvInfoSrvPortEntry 13 }

		
--  1.3.6.1.4.1.37950.1.1.6.1.1.8.7.1.14
		-- 1.3.6.1.4.1.37950.1.1.6.1.1.8.7.1.14
		gOnuSrvInfoSrvPortVid OBJECT-TYPE
			SYNTAX Integer32 (0..4094)
			MAX-ACCESS read-only
			STATUS current
			DESCRIPTION
				"Description."
			::= { gOnuSrvInfoSrvPortEntry 14 }

		
--  1.3.6.1.4.1.37950.1.1.6.1.1.8.7.1.15
		-- 1.3.6.1.4.1.37950.1.1.6.1.1.8.7.1.15
		gOnuSrvInfoSrvPortCos OBJECT-TYPE
			SYNTAX Integer32 (-1..7)
			MAX-ACCESS read-only
			STATUS current
			DESCRIPTION
				"Description."
			::= { gOnuSrvInfoSrvPortEntry 15 }

		
--  1.3.6.1.4.1.37950.1.1.6.1.1.8.7.1.16
		-- 1.3.6.1.4.1.37950.1.1.6.1.1.8.7.1.16
		gOnuSrvInfoSrvPortSVid OBJECT-TYPE
			SYNTAX Integer32 (0..4094)
			MAX-ACCESS read-only
			STATUS current
			DESCRIPTION
				"Description."
			::= { gOnuSrvInfoSrvPortEntry 16 }

		
--  1.3.6.1.4.1.37950.1.1.6.1.1.8.7.1.17
		-- 1.3.6.1.4.1.37950.1.1.6.1.1.8.7.1.17
		gOnuSrvInfoSrvPortSCos OBJECT-TYPE
			SYNTAX Integer32 (-1..7)
			MAX-ACCESS read-only
			STATUS current
			DESCRIPTION
				"Description."
			::= { gOnuSrvInfoSrvPortEntry 17 }

		
--  1.3.6.1.4.1.37950.1.1.6.1.1.8.8
		-- 1.3.6.1.4.1.37950.1.1.6.1.1.8.8
		gOnuSrvInfoTdTable OBJECT-TYPE
			SYNTAX SEQUENCE OF GOnuSrvInfoTdEntry
			MAX-ACCESS not-accessible
			STATUS current
			DESCRIPTION
				"Description."
			::= { gOnuSrvInfo 8 }

		
--  1.3.6.1.4.1.37950.1.1.6.1.1.8.8.1
		-- 1.3.6.1.4.1.37950.1.1.6.1.1.8.8.1
		gOnuSrvInfoTdEntry OBJECT-TYPE
			SYNTAX GOnuSrvInfoTdEntry
			MAX-ACCESS not-accessible
			STATUS current
			DESCRIPTION
				"Description."
			INDEX { gOnuSrvInfoTd }
			::= { gOnuSrvInfoTdTable 1 }

		
		GOnuSrvInfoTdEntry ::=
			SEQUENCE { 
				gOnuSrvInfoTd
					OCTET STRING
			 }

--  1.3.6.1.4.1.37950.1.1.6.1.1.8.8.1.1
		-- 1.3.6.1.4.1.37950.1.1.6.1.1.8.8.1.1
		gOnuSrvInfoTd OBJECT-TYPE
			SYNTAX OCTET STRING
			MAX-ACCESS read-only
			STATUS current
			DESCRIPTION
				"Description."
			::= { gOnuSrvInfoTdEntry 1 }

		
--  1.3.6.1.4.1.37950.1.1.6.1.1.8.9
		-- 1.3.6.1.4.1.37950.1.1.6.1.1.8.9
		gOnuSrvInfoPortVlanTable OBJECT-TYPE
			SYNTAX SEQUENCE OF GOnuSrvInfoPortVlanEntry
			MAX-ACCESS not-accessible
			STATUS current
			DESCRIPTION
				"Description."
			::= { gOnuSrvInfo 9 }

		
--  1.3.6.1.4.1.37950.1.1.6.1.1.8.9.1
		-- 1.3.6.1.4.1.37950.1.1.6.1.1.8.9.1
		gOnuSrvInfoPortVlanEntry OBJECT-TYPE
			SYNTAX GOnuSrvInfoPortVlanEntry
			MAX-ACCESS not-accessible
			STATUS current
			DESCRIPTION
				"Description."
			INDEX { gOnuSrvInfoPortVlanPonInx, gOnuSrvInfoPortVlanOnuInx, gOnuSrvInfoPortVlanName }
			::= { gOnuSrvInfoPortVlanTable 1 }

		
		GOnuSrvInfoPortVlanEntry ::=
			SEQUENCE { 
				gOnuSrvInfoPortVlanPonInx
					Integer32,
				gOnuSrvInfoPortVlanOnuInx
					Integer32,
				gOnuSrvInfoPortVlanName
					OCTET STRING,
				gOnuSrvInfoPortVlanMode
					INTEGER,
				gOnuSrvInfoPortVlanTPri
					Integer32,
				gOnuSrvInfoPortVlanList
					OCTET STRING,
				gOnuSrvInfoPortVlanVid
					Integer32,
				gOnuSrvInfoPortVlanPri
					Integer32,
				gOnuSrvInfoPortVlanTslCVid
					Integer32,
				gOnuSrvInfoPortVlanTslCPri
					Integer32,
				gOnuSrvInfoPortVlanTslSVid
					Integer32,
				gOnuSrvInfoPortVlanTslSPri
					Integer32
			 }

--  1.3.6.1.4.1.37950.1.1.6.1.1.8.9.1.1
		-- 1.3.6.1.4.1.37950.1.1.6.1.1.8.9.1.1
		gOnuSrvInfoPortVlanPonInx OBJECT-TYPE
			SYNTAX Integer32 (1..16)
			MAX-ACCESS read-only
			STATUS current
			DESCRIPTION
				"Description."
			::= { gOnuSrvInfoPortVlanEntry 1 }

		
--  1.3.6.1.4.1.37950.1.1.6.1.1.8.9.1.2
		-- 1.3.6.1.4.1.37950.1.1.6.1.1.8.9.1.2
		gOnuSrvInfoPortVlanOnuInx OBJECT-TYPE
			SYNTAX Integer32 (1..128)
			MAX-ACCESS read-only
			STATUS current
			DESCRIPTION
				"Description."
			::= { gOnuSrvInfoPortVlanEntry 2 }

		
--  1.3.6.1.4.1.37950.1.1.6.1.1.8.9.1.3
		-- 1.3.6.1.4.1.37950.1.1.6.1.1.8.9.1.3
		gOnuSrvInfoPortVlanName OBJECT-TYPE
			SYNTAX OCTET STRING
			MAX-ACCESS read-only
			STATUS current
			DESCRIPTION
				"Description."
			::= { gOnuSrvInfoPortVlanEntry 3 }

		
--  1.3.6.1.4.1.37950.1.1.6.1.1.8.9.1.4
		-- 1.3.6.1.4.1.37950.1.1.6.1.1.8.9.1.4
		gOnuSrvInfoPortVlanMode OBJECT-TYPE
			SYNTAX INTEGER
				{
				transparent(1),
				trunk(2),
				tag(3),
				hybrid(4),
				translate(5)
				}
			MAX-ACCESS read-only
			STATUS current
			DESCRIPTION
				"Description."
			::= { gOnuSrvInfoPortVlanEntry 4 }

		
--  1.3.6.1.4.1.37950.1.1.6.1.1.8.9.1.5
		-- 1.3.6.1.4.1.37950.1.1.6.1.1.8.9.1.5
		gOnuSrvInfoPortVlanTPri OBJECT-TYPE
			SYNTAX Integer32
			MAX-ACCESS read-only
			STATUS current
			DESCRIPTION
				"Description."
			::= { gOnuSrvInfoPortVlanEntry 5 }

		
--  1.3.6.1.4.1.37950.1.1.6.1.1.8.9.1.6
		-- 1.3.6.1.4.1.37950.1.1.6.1.1.8.9.1.6
		gOnuSrvInfoPortVlanList OBJECT-TYPE
			SYNTAX OCTET STRING
			MAX-ACCESS read-only
			STATUS current
			DESCRIPTION
				"Description."
			::= { gOnuSrvInfoPortVlanEntry 6 }

		
--  1.3.6.1.4.1.37950.1.1.6.1.1.8.9.1.7
		-- 1.3.6.1.4.1.37950.1.1.6.1.1.8.9.1.7
		gOnuSrvInfoPortVlanVid OBJECT-TYPE
			SYNTAX Integer32 (1..4094)
			MAX-ACCESS read-only
			STATUS current
			DESCRIPTION
				"Description."
			::= { gOnuSrvInfoPortVlanEntry 7 }

		
--  1.3.6.1.4.1.37950.1.1.6.1.1.8.9.1.8
		-- 1.3.6.1.4.1.37950.1.1.6.1.1.8.9.1.8
		gOnuSrvInfoPortVlanPri OBJECT-TYPE
			SYNTAX Integer32 (0..8)
			MAX-ACCESS read-only
			STATUS current
			DESCRIPTION
				"Description."
			::= { gOnuSrvInfoPortVlanEntry 8 }

		
--  1.3.6.1.4.1.37950.1.1.6.1.1.8.9.1.9
		-- 1.3.6.1.4.1.37950.1.1.6.1.1.8.9.1.9
		gOnuSrvInfoPortVlanTslCVid OBJECT-TYPE
			SYNTAX Integer32 (1..4094)
			MAX-ACCESS read-only
			STATUS current
			DESCRIPTION
				"Description."
			::= { gOnuSrvInfoPortVlanEntry 9 }

		
--  1.3.6.1.4.1.37950.1.1.6.1.1.8.9.1.10
		-- 1.3.6.1.4.1.37950.1.1.6.1.1.8.9.1.10
		gOnuSrvInfoPortVlanTslCPri OBJECT-TYPE
			SYNTAX Integer32 (0..8)
			MAX-ACCESS read-only
			STATUS current
			DESCRIPTION
				"Description."
			::= { gOnuSrvInfoPortVlanEntry 10 }

		
--  1.3.6.1.4.1.37950.1.1.6.1.1.8.9.1.11
		-- 1.3.6.1.4.1.37950.1.1.6.1.1.8.9.1.11
		gOnuSrvInfoPortVlanTslSVid OBJECT-TYPE
			SYNTAX Integer32 (1..4094)
			MAX-ACCESS read-only
			STATUS current
			DESCRIPTION
				"Description."
			::= { gOnuSrvInfoPortVlanEntry 11 }

		
--  1.3.6.1.4.1.37950.1.1.6.1.1.8.9.1.12
		-- 1.3.6.1.4.1.37950.1.1.6.1.1.8.9.1.12
		gOnuSrvInfoPortVlanTslSPri OBJECT-TYPE
			SYNTAX Integer32 (0..8)
			MAX-ACCESS read-only
			STATUS current
			DESCRIPTION
				"Description."
			::= { gOnuSrvInfoPortVlanEntry 12 }

		
--  1.3.6.1.4.1.37950.1.1.6.1.1.8.10
		-- 1.3.6.1.4.1.37950.1.1.6.1.1.8.10
		gOnuSrvInfoTeTable OBJECT-TYPE
			SYNTAX SEQUENCE OF GOnuSrvInfoTeEntry
			MAX-ACCESS not-accessible
			STATUS current
			DESCRIPTION
				"Description."
			::= { gOnuSrvInfo 10 }

		
--  1.3.6.1.4.1.37950.1.1.6.1.1.8.10.1
		-- 1.3.6.1.4.1.37950.1.1.6.1.1.8.10.1
		gOnuSrvInfoTeEntry OBJECT-TYPE
			SYNTAX GOnuSrvInfoTeEntry
			MAX-ACCESS not-accessible
			STATUS current
			DESCRIPTION
				"Description."
			INDEX { gOnuSrvInfoTe }
			::= { gOnuSrvInfoTeTable 1 }

		
		GOnuSrvInfoTeEntry ::=
			SEQUENCE { 
				gOnuSrvInfoTe
					OCTET STRING
			 }

--  1.3.6.1.4.1.37950.1.1.6.1.1.8.10.1.1
		-- 1.3.6.1.4.1.37950.1.1.6.1.1.8.10.1.1
		gOnuSrvInfoTe OBJECT-TYPE
			SYNTAX OCTET STRING
			MAX-ACCESS read-only
			STATUS current
			DESCRIPTION
				"Description."
			::= { gOnuSrvInfoTeEntry 1 }

		
--  1.3.6.1.4.1.37950.1.1.6.1.1.8.11
		-- 1.3.6.1.4.1.37950.1.1.6.1.1.8.11
		gOnuSrvInfoMVlanTable OBJECT-TYPE
			SYNTAX SEQUENCE OF GOnuSrvInfoMVlanEntry
			MAX-ACCESS not-accessible
			STATUS current
			DESCRIPTION
				"Description."
			::= { gOnuSrvInfo 11 }

		
--  1.3.6.1.4.1.37950.1.1.6.1.1.8.11.1
		-- 1.3.6.1.4.1.37950.1.1.6.1.1.8.11.1
		gOnuSrvInfoMVlanEntry OBJECT-TYPE
			SYNTAX GOnuSrvInfoMVlanEntry
			MAX-ACCESS not-accessible
			STATUS current
			DESCRIPTION
				"Description."
			INDEX { gOnuSrvInfoMVlanPonInx, gOnuSrvInfoMVlanOnuInx }
			::= { gOnuSrvInfoMVlanTable 1 }

		
		GOnuSrvInfoMVlanEntry ::=
			SEQUENCE { 
				gOnuSrvInfoMVlanPonInx
					Integer32,
				gOnuSrvInfoMVlanOnuInx
					Integer32,
				gOnuSrvInfoMVlanList
					OCTET STRING
			 }

--  1.3.6.1.4.1.37950.1.1.6.1.1.8.11.1.1
		-- 1.3.6.1.4.1.37950.1.1.6.1.1.8.11.1.1
		gOnuSrvInfoMVlanPonInx OBJECT-TYPE
			SYNTAX Integer32 (1..16)
			MAX-ACCESS read-only
			STATUS current
			DESCRIPTION
				"Description."
			::= { gOnuSrvInfoMVlanEntry 1 }

		
--  1.3.6.1.4.1.37950.1.1.6.1.1.8.11.1.2
		-- 1.3.6.1.4.1.37950.1.1.6.1.1.8.11.1.2
		gOnuSrvInfoMVlanOnuInx OBJECT-TYPE
			SYNTAX Integer32 (1..128)
			MAX-ACCESS read-only
			STATUS current
			DESCRIPTION
				"Description."
			::= { gOnuSrvInfoMVlanEntry 2 }

		
--  1.3.6.1.4.1.37950.1.1.6.1.1.8.11.1.3
		-- 1.3.6.1.4.1.37950.1.1.6.1.1.8.11.1.3
		gOnuSrvInfoMVlanList OBJECT-TYPE
			SYNTAX OCTET STRING
			MAX-ACCESS read-only
			STATUS current
			DESCRIPTION
				"Description."
			::= { gOnuSrvInfoMVlanEntry 3 }

		
--  1.3.6.1.4.1.37950.1.1.6.1.1.8.12
		-- 1.3.6.1.4.1.37950.1.1.6.1.1.8.12
		gOnuSrvInfoTfTable OBJECT-TYPE
			SYNTAX SEQUENCE OF GOnuSrvInfoTfEntry
			MAX-ACCESS not-accessible
			STATUS current
			DESCRIPTION
				"Description."
			::= { gOnuSrvInfo 12 }

		
--  1.3.6.1.4.1.37950.1.1.6.1.1.8.12.1
		-- 1.3.6.1.4.1.37950.1.1.6.1.1.8.12.1
		gOnuSrvInfoTfEntry OBJECT-TYPE
			SYNTAX GOnuSrvInfoTfEntry
			MAX-ACCESS not-accessible
			STATUS current
			DESCRIPTION
				"Description."
			INDEX { gOnuSrvInfoTf }
			::= { gOnuSrvInfoTfTable 1 }

		
		GOnuSrvInfoTfEntry ::=
			SEQUENCE { 
				gOnuSrvInfoTf
					OCTET STRING
			 }

--  1.3.6.1.4.1.37950.1.1.6.1.1.8.12.1.1
		-- 1.3.6.1.4.1.37950.1.1.6.1.1.8.12.1.1
		gOnuSrvInfoTf OBJECT-TYPE
			SYNTAX OCTET STRING
			MAX-ACCESS read-only
			STATUS current
			DESCRIPTION
				"Description."
			::= { gOnuSrvInfoTfEntry 1 }

		
--  1.3.6.1.4.1.37950.1.1.6.1.1.8.13
		-- 1.3.6.1.4.1.37950.1.1.6.1.1.8.13
		gOnuSrvInfoMVlanStripTable OBJECT-TYPE
			SYNTAX SEQUENCE OF GOnuSrvInfoMVlanStripEntry
			MAX-ACCESS not-accessible
			STATUS current
			DESCRIPTION
				"Description."
			::= { gOnuSrvInfo 13 }

		
--  1.3.6.1.4.1.37950.1.1.6.1.1.8.13.1
		-- 1.3.6.1.4.1.37950.1.1.6.1.1.8.13.1
		gOnuSrvInfoMVlanStripEntry OBJECT-TYPE
			SYNTAX GOnuSrvInfoMVlanStripEntry
			MAX-ACCESS not-accessible
			STATUS current
			DESCRIPTION
				"Description."
			INDEX { gOnuSrvInfoMVlanStripPonInx, gOnuSrvInfoMVlanStripOnuInx, gOnuSrvInfoMVlanStripPortName }
			::= { gOnuSrvInfoMVlanStripTable 1 }

		
		GOnuSrvInfoMVlanStripEntry ::=
			SEQUENCE { 
				gOnuSrvInfoMVlanStripPonInx
					Integer32,
				gOnuSrvInfoMVlanStripOnuInx
					Integer32,
				gOnuSrvInfoMVlanStripPortName
					OCTET STRING,
				gOnuSrvInfoMVlanStripTransList
					OCTET STRING
			 }

--  1.3.6.1.4.1.37950.1.1.6.1.1.8.13.1.1
		-- 1.3.6.1.4.1.37950.1.1.6.1.1.8.13.1.1
		gOnuSrvInfoMVlanStripPonInx OBJECT-TYPE
			SYNTAX Integer32 (1..16)
			MAX-ACCESS read-only
			STATUS current
			DESCRIPTION
				"Description."
			::= { gOnuSrvInfoMVlanStripEntry 1 }

		
--  1.3.6.1.4.1.37950.1.1.6.1.1.8.13.1.2
		-- 1.3.6.1.4.1.37950.1.1.6.1.1.8.13.1.2
		gOnuSrvInfoMVlanStripOnuInx OBJECT-TYPE
			SYNTAX Integer32 (1..128)
			MAX-ACCESS read-write
			STATUS current
			DESCRIPTION
				"Description."
			::= { gOnuSrvInfoMVlanStripEntry 2 }

		
--  1.3.6.1.4.1.37950.1.1.6.1.1.8.13.1.3
		-- 1.3.6.1.4.1.37950.1.1.6.1.1.8.13.1.3
		gOnuSrvInfoMVlanStripPortName OBJECT-TYPE
			SYNTAX OCTET STRING
			MAX-ACCESS read-only
			STATUS current
			DESCRIPTION
				"Description."
			::= { gOnuSrvInfoMVlanStripEntry 3 }

		
--  1.3.6.1.4.1.37950.1.1.6.1.1.8.13.1.4
		-- 1.3.6.1.4.1.37950.1.1.6.1.1.8.13.1.4
		gOnuSrvInfoMVlanStripTransList OBJECT-TYPE
			SYNTAX OCTET STRING
			MAX-ACCESS read-only
			STATUS current
			DESCRIPTION
				"Description."
			::= { gOnuSrvInfoMVlanStripEntry 4 }

		
--  1.3.6.1.4.1.37950.1.1.6.1.1.8.14
		-- 1.3.6.1.4.1.37950.1.1.6.1.1.8.14
		gOnuSrvInfoTgTable OBJECT-TYPE
			SYNTAX SEQUENCE OF GOnuSrvInfoTgEntry
			MAX-ACCESS not-accessible
			STATUS current
			DESCRIPTION
				"Description."
			::= { gOnuSrvInfo 14 }

		
--  1.3.6.1.4.1.37950.1.1.6.1.1.8.14.1
		-- 1.3.6.1.4.1.37950.1.1.6.1.1.8.14.1
		gOnuSrvInfoTgEntry OBJECT-TYPE
			SYNTAX GOnuSrvInfoTgEntry
			MAX-ACCESS not-accessible
			STATUS current
			DESCRIPTION
				"Description."
			INDEX { gOnuSrvInfoTg }
			::= { gOnuSrvInfoTgTable 1 }

		
		GOnuSrvInfoTgEntry ::=
			SEQUENCE { 
				gOnuSrvInfoTg
					OCTET STRING
			 }

--  1.3.6.1.4.1.37950.1.1.6.1.1.8.14.1.1
		-- 1.3.6.1.4.1.37950.1.1.6.1.1.8.14.1.1
		gOnuSrvInfoTg OBJECT-TYPE
			SYNTAX OCTET STRING
			MAX-ACCESS read-only
			STATUS current
			DESCRIPTION
				"Description."
			::= { gOnuSrvInfoTgEntry 1 }

		
--  1.3.6.1.4.1.37950.1.1.6.1.1.8.15
		-- 1.3.6.1.4.1.37950.1.1.6.1.1.8.15
		gOnuSrvInfoPortTable OBJECT-TYPE
			SYNTAX SEQUENCE OF GOnuSrvInfoPortEntry
			MAX-ACCESS not-accessible
			STATUS current
			DESCRIPTION
				"Description."
			::= { gOnuSrvInfo 15 }

		
--  1.3.6.1.4.1.37950.1.1.6.1.1.8.15.1
		-- 1.3.6.1.4.1.37950.1.1.6.1.1.8.15.1
		gOnuSrvInfoPortEntry OBJECT-TYPE
			SYNTAX GOnuSrvInfoPortEntry
			MAX-ACCESS not-accessible
			STATUS current
			DESCRIPTION
				"Description."
			INDEX { gOnuSrvInfoPortPonInx, gOnuSrvInfoPortOnuInx, gOnuSrvInfoPortId }
			::= { gOnuSrvInfoPortTable 1 }

		
		GOnuSrvInfoPortEntry ::=
			SEQUENCE { 
				gOnuSrvInfoPortPonInx
					Integer32,
				gOnuSrvInfoPortOnuInx
					Integer32,
				gOnuSrvInfoPortId
					Integer32,
				gOnuSrvInfoPortState
					INTEGER,
				gOnuSrvInfoPortLoopDetect
					INTEGER,
				gOnuSrvInfoPortSpeed
					INTEGER,
				gOnuSrvInfoPortMacLimit
					Integer32
			 }

--  1.3.6.1.4.1.37950.1.1.6.1.1.8.15.1.1
		-- 1.3.6.1.4.1.37950.1.1.6.1.1.8.15.1.1
		gOnuSrvInfoPortPonInx OBJECT-TYPE
			SYNTAX Integer32 (1..16)
			MAX-ACCESS read-only
			STATUS current
			DESCRIPTION
				"Description."
			::= { gOnuSrvInfoPortEntry 1 }

		
--  1.3.6.1.4.1.37950.1.1.6.1.1.8.15.1.2
		-- 1.3.6.1.4.1.37950.1.1.6.1.1.8.15.1.2
		gOnuSrvInfoPortOnuInx OBJECT-TYPE
			SYNTAX Integer32 (1..128)
			MAX-ACCESS read-only
			STATUS current
			DESCRIPTION
				"Description."
			::= { gOnuSrvInfoPortEntry 2 }

		
--  1.3.6.1.4.1.37950.1.1.6.1.1.8.15.1.3
		-- 1.3.6.1.4.1.37950.1.1.6.1.1.8.15.1.3
		gOnuSrvInfoPortId OBJECT-TYPE
			SYNTAX Integer32
			MAX-ACCESS read-only
			STATUS current
			DESCRIPTION
				"Description."
			::= { gOnuSrvInfoPortEntry 3 }

		
--  1.3.6.1.4.1.37950.1.1.6.1.1.8.15.1.4
		-- 1.3.6.1.4.1.37950.1.1.6.1.1.8.15.1.4
		gOnuSrvInfoPortState OBJECT-TYPE
			SYNTAX INTEGER
				{
				enable(0),
				disable(1)
				}
			MAX-ACCESS read-only
			STATUS current
			DESCRIPTION
				"Description."
			::= { gOnuSrvInfoPortEntry 4 }

		
--  1.3.6.1.4.1.37950.1.1.6.1.1.8.15.1.5
		-- 1.3.6.1.4.1.37950.1.1.6.1.1.8.15.1.5
		gOnuSrvInfoPortLoopDetect OBJECT-TYPE
			SYNTAX INTEGER
				{
				enable(0),
				disable(1)
				}
			MAX-ACCESS read-only
			STATUS current
			DESCRIPTION
				"Description."
			::= { gOnuSrvInfoPortEntry 5 }

		
--  1.3.6.1.4.1.37950.1.1.6.1.1.8.15.1.6
		-- 1.3.6.1.4.1.37950.1.1.6.1.1.8.15.1.6
		gOnuSrvInfoPortSpeed OBJECT-TYPE
			SYNTAX INTEGER
				{
				auto(1),
				half-10(2),
				full-10(3),
				half-100(4),
				full-100(5),
				full-1000(6),
				half-1000(7),
				full-10g(8),
				full-2point5g(9),
				full-5g(10),
				full-25g(11),
				full-40g(12)
				}
			MAX-ACCESS read-only
			STATUS current
			DESCRIPTION
				"Description."
			::= { gOnuSrvInfoPortEntry 6 }

		
--  1.3.6.1.4.1.37950.1.1.6.1.1.8.15.1.7
		-- 1.3.6.1.4.1.37950.1.1.6.1.1.8.15.1.7
		gOnuSrvInfoPortMacLimit OBJECT-TYPE
			SYNTAX Integer32 (0..255)
			MAX-ACCESS read-write
			STATUS current
			DESCRIPTION
				"Description."
			::= { gOnuSrvInfoPortEntry 7 }

		
--  1.3.6.1.4.1.37950.1.1.6.1.1.8.16
		-- 1.3.6.1.4.1.37950.1.1.6.1.1.8.16
		gOnuSrvInfoThTable OBJECT-TYPE
			SYNTAX SEQUENCE OF GOnuSrvInfoThEntry
			MAX-ACCESS not-accessible
			STATUS current
			DESCRIPTION
				"Description."
			::= { gOnuSrvInfo 16 }

		
--  1.3.6.1.4.1.37950.1.1.6.1.1.8.16.1
		-- 1.3.6.1.4.1.37950.1.1.6.1.1.8.16.1
		gOnuSrvInfoThEntry OBJECT-TYPE
			SYNTAX GOnuSrvInfoThEntry
			MAX-ACCESS not-accessible
			STATUS current
			DESCRIPTION
				"Description."
			INDEX { gOnuSrvInfoTh }
			::= { gOnuSrvInfoThTable 1 }

		
		GOnuSrvInfoThEntry ::=
			SEQUENCE { 
				gOnuSrvInfoTh
					OCTET STRING
			 }

--  1.3.6.1.4.1.37950.1.1.6.1.1.8.16.1.1
		-- 1.3.6.1.4.1.37950.1.1.6.1.1.8.16.1.1
		gOnuSrvInfoTh OBJECT-TYPE
			SYNTAX OCTET STRING
			MAX-ACCESS read-only
			STATUS current
			DESCRIPTION
				"Description."
			::= { gOnuSrvInfoThEntry 1 }

		
--  1.3.6.1.4.1.37950.1.1.6.1.1.8.17
		-- 1.3.6.1.4.1.37950.1.1.6.1.1.8.17
		gOnuSrvInfoIphostTable OBJECT-TYPE
			SYNTAX SEQUENCE OF GOnuSrvInfoIphostEntry
			MAX-ACCESS not-accessible
			STATUS current
			DESCRIPTION
				"Description."
			::= { gOnuSrvInfo 17 }

		
--  1.3.6.1.4.1.37950.1.1.6.1.1.8.17.1
		-- 1.3.6.1.4.1.37950.1.1.6.1.1.8.17.1
		gOnuSrvInfoIphostEntry OBJECT-TYPE
			SYNTAX GOnuSrvInfoIphostEntry
			MAX-ACCESS not-accessible
			STATUS current
			DESCRIPTION
				"Description."
			INDEX { gOnuSrvInfoIphostPonInx, gOnuSrvInfoIphostOnuInx, gOnuSrvInfoIphostId }
			::= { gOnuSrvInfoIphostTable 1 }

		
		GOnuSrvInfoIphostEntry ::=
			SEQUENCE { 
				gOnuSrvInfoIphostPonInx
					Integer32,
				gOnuSrvInfoIphostOnuInx
					Integer32,
				gOnuSrvInfoIphostId
					Integer32,
				gOnuSrvInfoIphostDesc
					OCTET STRING,
				gOnuSrvInfoIphostIpMode
					INTEGER,
				gOnuSrvInfoIphostIpAddr
					IpAddress,
				gOnuSrvInfoIphostMask
					IpAddress,
				gOnuSrvInfoIphostGateway
					IpAddress,
				gOnuSrvInfoIphostdns1
					IpAddress,
				gOnuSrvInfoIphostdns2
					IpAddress,
				gOnuSrvInfoIphostVlan
					Integer32,
				gOnuSrvInfoIphostVlanPri
					Integer32
			 }

--  1.3.6.1.4.1.37950.1.1.6.1.1.8.17.1.1
		-- 1.3.6.1.4.1.37950.1.1.6.1.1.8.17.1.1
		gOnuSrvInfoIphostPonInx OBJECT-TYPE
			SYNTAX Integer32 (1..16)
			MAX-ACCESS read-only
			STATUS current
			DESCRIPTION
				"Description."
			::= { gOnuSrvInfoIphostEntry 1 }

		
--  1.3.6.1.4.1.37950.1.1.6.1.1.8.17.1.2
		-- 1.3.6.1.4.1.37950.1.1.6.1.1.8.17.1.2
		gOnuSrvInfoIphostOnuInx OBJECT-TYPE
			SYNTAX Integer32 (1..128)
			MAX-ACCESS read-only
			STATUS current
			DESCRIPTION
				"Description."
			::= { gOnuSrvInfoIphostEntry 2 }

		
--  1.3.6.1.4.1.37950.1.1.6.1.1.8.17.1.3
		-- 1.3.6.1.4.1.37950.1.1.6.1.1.8.17.1.3
		gOnuSrvInfoIphostId OBJECT-TYPE
			SYNTAX Integer32
			MAX-ACCESS read-only
			STATUS current
			DESCRIPTION
				"Description."
			::= { gOnuSrvInfoIphostEntry 3 }

		
--  1.3.6.1.4.1.37950.1.1.6.1.1.8.17.1.4
		-- 1.3.6.1.4.1.37950.1.1.6.1.1.8.17.1.4
		gOnuSrvInfoIphostDesc OBJECT-TYPE
			SYNTAX OCTET STRING
			MAX-ACCESS read-only
			STATUS current
			DESCRIPTION
				"Description."
			::= { gOnuSrvInfoIphostEntry 4 }

		
--  1.3.6.1.4.1.37950.1.1.6.1.1.8.17.1.5
		-- 1.3.6.1.4.1.37950.1.1.6.1.1.8.17.1.5
		gOnuSrvInfoIphostIpMode OBJECT-TYPE
			SYNTAX INTEGER
				{
				dhcp(1),
				static_ip(2)
				}
			MAX-ACCESS read-only
			STATUS current
			DESCRIPTION
				"Description."
			::= { gOnuSrvInfoIphostEntry 5 }

		
--  1.3.6.1.4.1.37950.1.1.6.1.1.8.17.1.6
		-- 1.3.6.1.4.1.37950.1.1.6.1.1.8.17.1.6
		gOnuSrvInfoIphostIpAddr OBJECT-TYPE
			SYNTAX IpAddress
			MAX-ACCESS read-only
			STATUS current
			DESCRIPTION
				"Description."
			::= { gOnuSrvInfoIphostEntry 6 }

		
--  1.3.6.1.4.1.37950.1.1.6.1.1.8.17.1.7
		-- 1.3.6.1.4.1.37950.1.1.6.1.1.8.17.1.7
		gOnuSrvInfoIphostMask OBJECT-TYPE
			SYNTAX IpAddress
			MAX-ACCESS read-only
			STATUS current
			DESCRIPTION
				"Description."
			::= { gOnuSrvInfoIphostEntry 7 }

		
--  1.3.6.1.4.1.37950.1.1.6.1.1.8.17.1.8
		-- 1.3.6.1.4.1.37950.1.1.6.1.1.8.17.1.8
		gOnuSrvInfoIphostGateway OBJECT-TYPE
			SYNTAX IpAddress
			MAX-ACCESS read-only
			STATUS current
			DESCRIPTION
				"Description."
			::= { gOnuSrvInfoIphostEntry 8 }

		
--  1.3.6.1.4.1.37950.1.1.6.1.1.8.17.1.9
		-- 1.3.6.1.4.1.37950.1.1.6.1.1.8.17.1.9
		gOnuSrvInfoIphostdns1 OBJECT-TYPE
			SYNTAX IpAddress
			MAX-ACCESS read-only
			STATUS current
			DESCRIPTION
				"Description."
			::= { gOnuSrvInfoIphostEntry 9 }

		
--  1.3.6.1.4.1.37950.1.1.6.1.1.8.17.1.10
		-- 1.3.6.1.4.1.37950.1.1.6.1.1.8.17.1.10
		gOnuSrvInfoIphostdns2 OBJECT-TYPE
			SYNTAX IpAddress
			MAX-ACCESS read-only
			STATUS current
			DESCRIPTION
				"Description."
			::= { gOnuSrvInfoIphostEntry 10 }

		
--  1.3.6.1.4.1.37950.1.1.6.1.1.8.17.1.11
		-- 1.3.6.1.4.1.37950.1.1.6.1.1.8.17.1.11
		gOnuSrvInfoIphostVlan OBJECT-TYPE
			SYNTAX Integer32 (1..4094)
			MAX-ACCESS read-only
			STATUS current
			DESCRIPTION
				"Description."
			::= { gOnuSrvInfoIphostEntry 11 }

		
--  1.3.6.1.4.1.37950.1.1.6.1.1.8.17.1.12
		-- 1.3.6.1.4.1.37950.1.1.6.1.1.8.17.1.12
		gOnuSrvInfoIphostVlanPri OBJECT-TYPE
			SYNTAX Integer32 (1..15)
			MAX-ACCESS read-write
			STATUS current
			DESCRIPTION
				"Description."
			::= { gOnuSrvInfoIphostEntry 12 }

		
--  1.3.6.1.4.1.37950.1.1.6.1.1.8.18
		-- 1.3.6.1.4.1.37950.1.1.6.1.1.8.18
		gOnuSrvInfoTiTable OBJECT-TYPE
			SYNTAX SEQUENCE OF GOnuSrvInfoTiEntry
			MAX-ACCESS not-accessible
			STATUS current
			DESCRIPTION
				"Description."
			::= { gOnuSrvInfo 18 }

		
--  1.3.6.1.4.1.37950.1.1.6.1.1.8.18.1
		-- 1.3.6.1.4.1.37950.1.1.6.1.1.8.18.1
		gOnuSrvInfoTiEntry OBJECT-TYPE
			SYNTAX GOnuSrvInfoTiEntry
			MAX-ACCESS not-accessible
			STATUS current
			DESCRIPTION
				"Description."
			INDEX { gOnuSrvInfoTi }
			::= { gOnuSrvInfoTiTable 1 }

		
		GOnuSrvInfoTiEntry ::=
			SEQUENCE { 
				gOnuSrvInfoTi
					OCTET STRING
			 }

--  1.3.6.1.4.1.37950.1.1.6.1.1.8.18.1.1
		-- 1.3.6.1.4.1.37950.1.1.6.1.1.8.18.1.1
		gOnuSrvInfoTi OBJECT-TYPE
			SYNTAX OCTET STRING
			MAX-ACCESS read-only
			STATUS current
			DESCRIPTION
				"Description."
			::= { gOnuSrvInfoTiEntry 1 }

		
--  1.3.6.1.4.1.37950.1.1.6.1.1.8.19
		-- 1.3.6.1.4.1.37950.1.1.6.1.1.8.19
		gOnuSrvInfoiphostMaxIdTable OBJECT-TYPE
			SYNTAX SEQUENCE OF GOnuSrvInfoiphostMaxIdEntry
			MAX-ACCESS not-accessible
			STATUS current
			DESCRIPTION
				"Description."
			::= { gOnuSrvInfo 19 }

		
--  1.3.6.1.4.1.37950.1.1.6.1.1.8.19.1
		-- 1.3.6.1.4.1.37950.1.1.6.1.1.8.19.1
		gOnuSrvInfoiphostMaxIdEntry OBJECT-TYPE
			SYNTAX GOnuSrvInfoiphostMaxIdEntry
			MAX-ACCESS not-accessible
			STATUS current
			DESCRIPTION
				"Description."
			INDEX { gOnuSrvInfoiphostMaxIdPon, gOnuSrvInfoiphostMaxIdOnu }
			::= { gOnuSrvInfoiphostMaxIdTable 1 }

		
		GOnuSrvInfoiphostMaxIdEntry ::=
			SEQUENCE { 
				gOnuSrvInfoiphostMaxIdPon
					Integer32,
				gOnuSrvInfoiphostMaxIdOnu
					Integer32,
				gOnuSrvInfoiphostMaxIdValue
					Integer32
			 }

--  1.3.6.1.4.1.37950.1.1.6.1.1.8.19.1.1
		-- 1.3.6.1.4.1.37950.1.1.6.1.1.8.19.1.1
		gOnuSrvInfoiphostMaxIdPon OBJECT-TYPE
			SYNTAX Integer32 (1..16)
			MAX-ACCESS read-only
			STATUS current
			DESCRIPTION
				"Description."
			::= { gOnuSrvInfoiphostMaxIdEntry 1 }

		
--  1.3.6.1.4.1.37950.1.1.6.1.1.8.19.1.2
		-- 1.3.6.1.4.1.37950.1.1.6.1.1.8.19.1.2
		gOnuSrvInfoiphostMaxIdOnu OBJECT-TYPE
			SYNTAX Integer32 (1..128)
			MAX-ACCESS read-only
			STATUS current
			DESCRIPTION
				"Description."
			::= { gOnuSrvInfoiphostMaxIdEntry 2 }

		
--  1.3.6.1.4.1.37950.1.1.6.1.1.8.19.1.3
		-- 1.3.6.1.4.1.37950.1.1.6.1.1.8.19.1.3
		gOnuSrvInfoiphostMaxIdValue OBJECT-TYPE
			SYNTAX Integer32
			MAX-ACCESS read-only
			STATUS current
			DESCRIPTION
				"Description."
			::= { gOnuSrvInfoiphostMaxIdEntry 3 }

		
--  1.3.6.1.4.1.37950.1.1.6.1.1.8.20
		-- 1.3.6.1.4.1.37950.1.1.6.1.1.8.20
		gOnuSrvCATVTable OBJECT-TYPE
			SYNTAX SEQUENCE OF GOnuSrvCATVEntry
			MAX-ACCESS not-accessible
			STATUS current
			DESCRIPTION
				"Description."
			::= { gOnuSrvInfo 20 }

		
--  1.3.6.1.4.1.37950.1.1.6.1.1.8.20.1
		-- 1.3.6.1.4.1.37950.1.1.6.1.1.8.20.1
		gOnuSrvCATVEntry OBJECT-TYPE
			SYNTAX GOnuSrvCATVEntry
			MAX-ACCESS not-accessible
			STATUS current
			DESCRIPTION
				"Description."
			INDEX { gOnuSrvCATVPonInx, gOnuSrvCATVOnuInx }
			::= { gOnuSrvCATVTable 1 }

		
		GOnuSrvCATVEntry ::=
			SEQUENCE { 
				gOnuSrvCATVPonInx
					Integer32,
				gOnuSrvCATVOnuInx
					Integer32,
				gOnuSrvCATVInterface
					OCTET STRING,
				gOnuSrvCATVAdminState
					INTEGER,
				gOnuSrvCATVARC
					Integer32,
				gOnuSrvCATVARCInterval
					Integer32,
				gOnuSrvCATVPowerControl
					INTEGER
			 }

--  1.3.6.1.4.1.37950.1.1.6.1.1.8.20.1.1
		-- 1.3.6.1.4.1.37950.1.1.6.1.1.8.20.1.1
		gOnuSrvCATVPonInx OBJECT-TYPE
			SYNTAX Integer32
			MAX-ACCESS read-write
			STATUS current
			DESCRIPTION
				"Description."
			::= { gOnuSrvCATVEntry 1 }

		
--  1.3.6.1.4.1.37950.1.1.6.1.1.8.20.1.2
		-- 1.3.6.1.4.1.37950.1.1.6.1.1.8.20.1.2
		gOnuSrvCATVOnuInx OBJECT-TYPE
			SYNTAX Integer32
			MAX-ACCESS read-write
			STATUS current
			DESCRIPTION
				"Description."
			::= { gOnuSrvCATVEntry 2 }

		
--  1.3.6.1.4.1.37950.1.1.6.1.1.8.20.1.3
		-- 1.3.6.1.4.1.37950.1.1.6.1.1.8.20.1.3
		gOnuSrvCATVInterface OBJECT-TYPE
			SYNTAX OCTET STRING
			MAX-ACCESS read-write
			STATUS current
			DESCRIPTION
				"Description."
			::= { gOnuSrvCATVEntry 3 }

		
--  1.3.6.1.4.1.37950.1.1.6.1.1.8.20.1.4
		-- 1.3.6.1.4.1.37950.1.1.6.1.1.8.20.1.4
		gOnuSrvCATVAdminState OBJECT-TYPE
			SYNTAX INTEGER
				{
				unlock(1),
				lock(2)
				}
			MAX-ACCESS read-write
			STATUS current
			DESCRIPTION
				"Description."
			::= { gOnuSrvCATVEntry 4 }

		
--  1.3.6.1.4.1.37950.1.1.6.1.1.8.20.1.5
		-- 1.3.6.1.4.1.37950.1.1.6.1.1.8.20.1.5
		gOnuSrvCATVARC OBJECT-TYPE
			SYNTAX Integer32
			MAX-ACCESS read-write
			STATUS current
			DESCRIPTION
				"Description."
			::= { gOnuSrvCATVEntry 5 }

		
--  1.3.6.1.4.1.37950.1.1.6.1.1.8.20.1.6
		-- 1.3.6.1.4.1.37950.1.1.6.1.1.8.20.1.6
		gOnuSrvCATVARCInterval OBJECT-TYPE
			SYNTAX Integer32
			MAX-ACCESS read-write
			STATUS current
			DESCRIPTION
				"Description."
			::= { gOnuSrvCATVEntry 6 }

		
--  1.3.6.1.4.1.37950.1.1.6.1.1.8.20.1.7
		-- 1.3.6.1.4.1.37950.1.1.6.1.1.8.20.1.7
		gOnuSrvCATVPowerControl OBJECT-TYPE
			SYNTAX INTEGER
				{
				disable(1),
				enable(2)
				}
			MAX-ACCESS read-write
			STATUS current
			DESCRIPTION
				"Description."
			::= { gOnuSrvCATVEntry 7 }

		
--  1.3.6.1.4.1.37950.1.1.6.1.1.8.21
		-- 1.3.6.1.4.1.37950.1.1.6.1.1.8.21
		gOnuSrvTr069Table OBJECT-TYPE
			SYNTAX SEQUENCE OF GOnuSrvTr069Entry
			MAX-ACCESS not-accessible
			STATUS current
			DESCRIPTION
				"Description."
			::= { gOnuSrvInfo 21 }

		
--  1.3.6.1.4.1.37950.1.1.6.1.1.8.21.1
		-- 1.3.6.1.4.1.37950.1.1.6.1.1.8.21.1
		gOnuSrvTr069Entry OBJECT-TYPE
			SYNTAX GOnuSrvTr069Entry
			MAX-ACCESS not-accessible
			STATUS current
			DESCRIPTION
				"Description."
			INDEX { gOnuSrvTr069PonInx, gOnuSrvTr069OnuInx }
			::= { gOnuSrvTr069Table 1 }

		
		GOnuSrvTr069Entry ::=
			SEQUENCE { 
				gOnuSrvTr069PonInx
					Integer32,
				gOnuSrvTr069OnuInx
					Integer32,
				gOnuSrvTr069VeipId
					Integer32,
				gOnuSrvTr069State
					INTEGER,
				gOnuSrvTr069Addr
					OCTET STRING,
				gOnuSrvTr069Username
					OCTET STRING,
				gOnuSrvTr069Password
					OCTET STRING,
				gOnuSrvTr069Tag
					INTEGER,
				gOnuSrvTr069VlanId
					Integer32,
				gOnuSrvTr069Priority
					Integer32
			 }

--  1.3.6.1.4.1.37950.1.1.6.1.1.8.21.1.1
		-- 1.3.6.1.4.1.37950.1.1.6.1.1.8.21.1.1
		gOnuSrvTr069PonInx OBJECT-TYPE
			SYNTAX Integer32
			MAX-ACCESS read-write
			STATUS current
			DESCRIPTION
				"Description."
			::= { gOnuSrvTr069Entry 1 }

		
--  1.3.6.1.4.1.37950.1.1.6.1.1.8.21.1.2
		-- 1.3.6.1.4.1.37950.1.1.6.1.1.8.21.1.2
		gOnuSrvTr069OnuInx OBJECT-TYPE
			SYNTAX Integer32
			MAX-ACCESS read-write
			STATUS current
			DESCRIPTION
				"Description."
			::= { gOnuSrvTr069Entry 2 }

		
--  1.3.6.1.4.1.37950.1.1.6.1.1.8.21.1.3
		-- 1.3.6.1.4.1.37950.1.1.6.1.1.8.21.1.3
		gOnuSrvTr069VeipId OBJECT-TYPE
			SYNTAX Integer32
			MAX-ACCESS read-write
			STATUS current
			DESCRIPTION
				"Description."
			::= { gOnuSrvTr069Entry 3 }

		
--  1.3.6.1.4.1.37950.1.1.6.1.1.8.21.1.4
		-- 1.3.6.1.4.1.37950.1.1.6.1.1.8.21.1.4
		gOnuSrvTr069State OBJECT-TYPE
			SYNTAX INTEGER
				{
				lock(0),
				unlock(1)
				}
			MAX-ACCESS read-write
			STATUS current
			DESCRIPTION
				"Description."
			::= { gOnuSrvTr069Entry 4 }

		
--  1.3.6.1.4.1.37950.1.1.6.1.1.8.21.1.5
		-- 1.3.6.1.4.1.37950.1.1.6.1.1.8.21.1.5
		gOnuSrvTr069Addr OBJECT-TYPE
			SYNTAX OCTET STRING
			MAX-ACCESS read-write
			STATUS current
			DESCRIPTION
				"Description."
			::= { gOnuSrvTr069Entry 5 }

		
--  1.3.6.1.4.1.37950.1.1.6.1.1.8.21.1.6
		-- 1.3.6.1.4.1.37950.1.1.6.1.1.8.21.1.6
		gOnuSrvTr069Username OBJECT-TYPE
			SYNTAX OCTET STRING
			MAX-ACCESS read-write
			STATUS current
			DESCRIPTION
				"Description."
			::= { gOnuSrvTr069Entry 6 }

		
--  1.3.6.1.4.1.37950.1.1.6.1.1.8.21.1.7
		-- 1.3.6.1.4.1.37950.1.1.6.1.1.8.21.1.7
		gOnuSrvTr069Password OBJECT-TYPE
			SYNTAX OCTET STRING
			MAX-ACCESS read-write
			STATUS current
			DESCRIPTION
				"Description."
			::= { gOnuSrvTr069Entry 7 }

		
--  1.3.6.1.4.1.37950.1.1.6.1.1.8.21.1.8
		-- 1.3.6.1.4.1.37950.1.1.6.1.1.8.21.1.8
		gOnuSrvTr069Tag OBJECT-TYPE
			SYNTAX INTEGER
				{
				disable(0),
				enable(1)
				}
			MAX-ACCESS read-write
			STATUS current
			DESCRIPTION
				"Description."
			::= { gOnuSrvTr069Entry 8 }

		
--  1.3.6.1.4.1.37950.1.1.6.1.1.8.21.1.9
		-- 1.3.6.1.4.1.37950.1.1.6.1.1.8.21.1.9
		gOnuSrvTr069VlanId OBJECT-TYPE
			SYNTAX Integer32
			MAX-ACCESS read-write
			STATUS current
			DESCRIPTION
				"Description."
			::= { gOnuSrvTr069Entry 9 }

		
--  1.3.6.1.4.1.37950.1.1.6.1.1.8.21.1.10
		-- 1.3.6.1.4.1.37950.1.1.6.1.1.8.21.1.10
		gOnuSrvTr069Priority OBJECT-TYPE
			SYNTAX Integer32
			MAX-ACCESS read-write
			STATUS current
			DESCRIPTION
				"Description."
			::= { gOnuSrvTr069Entry 10 }

		
--  1.3.6.1.4.1.37950.1.1.6.1.1.8.22
		-- 1.3.6.1.4.1.37950.1.1.6.1.1.8.22
		gOnuSrvFecTable OBJECT-TYPE
			SYNTAX SEQUENCE OF GOnuSrvFecEntry
			MAX-ACCESS not-accessible
			STATUS current
			DESCRIPTION
				"Description."
			::= { gOnuSrvInfo 22 }

		
--  1.3.6.1.4.1.37950.1.1.6.1.1.8.22.1
		-- 1.3.6.1.4.1.37950.1.1.6.1.1.8.22.1
		gOnuSrvFecEntry OBJECT-TYPE
			SYNTAX GOnuSrvFecEntry
			MAX-ACCESS not-accessible
			STATUS current
			DESCRIPTION
				"Description."
			INDEX { gOnuSrvFecPonInx, gOnuSrvFecOnuInx }
			::= { gOnuSrvFecTable 1 }

		
		GOnuSrvFecEntry ::=
			SEQUENCE { 
				gOnuSrvFecPonInx
					Integer32,
				gOnuSrvFecOnuInx
					Integer32,
				gOnuSrvFecState
					INTEGER
			 }

--  1.3.6.1.4.1.37950.1.1.6.1.1.8.22.1.1
		-- 1.3.6.1.4.1.37950.1.1.6.1.1.8.22.1.1
		gOnuSrvFecPonInx OBJECT-TYPE
			SYNTAX Integer32
			MAX-ACCESS read-write
			STATUS current
			DESCRIPTION
				"Description."
			::= { gOnuSrvFecEntry 1 }

		
--  1.3.6.1.4.1.37950.1.1.6.1.1.8.22.1.2
		-- 1.3.6.1.4.1.37950.1.1.6.1.1.8.22.1.2
		gOnuSrvFecOnuInx OBJECT-TYPE
			SYNTAX Integer32
			MAX-ACCESS read-write
			STATUS current
			DESCRIPTION
				"Description."
			::= { gOnuSrvFecEntry 2 }

		
--  1.3.6.1.4.1.37950.1.1.6.1.1.8.22.1.3
		-- 1.3.6.1.4.1.37950.1.1.6.1.1.8.22.1.3
		gOnuSrvFecState OBJECT-TYPE
			SYNTAX INTEGER
				{
				disable(0),
				enable(1)
				}
			MAX-ACCESS read-write
			STATUS current
			DESCRIPTION
				"Description."
			::= { gOnuSrvFecEntry 3 }

		
--  1.3.6.1.4.1.37950.1.1.6.1.1.8.23
		-- 1.3.6.1.4.1.37950.1.1.6.1.1.8.23
		gOnuSrvBerTable OBJECT-TYPE
			SYNTAX SEQUENCE OF GOnuSrvBerEntry
			MAX-ACCESS not-accessible
			STATUS current
			DESCRIPTION
				"Description."
			::= { gOnuSrvInfo 23 }

		
--  1.3.6.1.4.1.37950.1.1.6.1.1.8.23.1
		-- 1.3.6.1.4.1.37950.1.1.6.1.1.8.23.1
		gOnuSrvBerEntry OBJECT-TYPE
			SYNTAX GOnuSrvBerEntry
			MAX-ACCESS not-accessible
			STATUS current
			DESCRIPTION
				"Description."
			INDEX { gOnuSrvBerPonInx, gOnuSrvBerOnuInx }
			::= { gOnuSrvBerTable 1 }

		
		GOnuSrvBerEntry ::=
			SEQUENCE { 
				gOnuSrvBerPonInx
					Integer32,
				gOnuSrvBerOnuInx
					Integer32,
				gOnuSrvBerUp
					OCTET STRING,
				gOnuSrvBerDown
					OCTET STRING
			 }

--  1.3.6.1.4.1.37950.1.1.6.1.1.8.23.1.1
		-- 1.3.6.1.4.1.37950.1.1.6.1.1.8.23.1.1
		gOnuSrvBerPonInx OBJECT-TYPE
			SYNTAX Integer32
			MAX-ACCESS read-write
			STATUS current
			DESCRIPTION
				"Description."
			::= { gOnuSrvBerEntry 1 }

		
--  1.3.6.1.4.1.37950.1.1.6.1.1.8.23.1.2
		-- 1.3.6.1.4.1.37950.1.1.6.1.1.8.23.1.2
		gOnuSrvBerOnuInx OBJECT-TYPE
			SYNTAX Integer32
			MAX-ACCESS read-write
			STATUS current
			DESCRIPTION
				"Description."
			::= { gOnuSrvBerEntry 2 }

		
--  1.3.6.1.4.1.37950.1.1.6.1.1.8.23.1.3
		-- 1.3.6.1.4.1.37950.1.1.6.1.1.8.23.1.3
		gOnuSrvBerUp OBJECT-TYPE
			SYNTAX OCTET STRING
			MAX-ACCESS read-write
			STATUS current
			DESCRIPTION
				"Description."
			::= { gOnuSrvBerEntry 3 }

		
--  1.3.6.1.4.1.37950.1.1.6.1.1.8.23.1.4
		-- 1.3.6.1.4.1.37950.1.1.6.1.1.8.23.1.4
		gOnuSrvBerDown OBJECT-TYPE
			SYNTAX OCTET STRING
			MAX-ACCESS read-write
			STATUS current
			DESCRIPTION
				"Description."
			::= { gOnuSrvBerEntry 4 }

		
--  1.3.6.1.4.1.37950.1.1.6.1.1.8.20
		-- 1.3.6.1.4.1.37950.1.1.6.1.1.8.24
		gOnuSrvCATVUniTable OBJECT-TYPE
			SYNTAX SEQUENCE OF GOnuSrvCATVUniEntry
			MAX-ACCESS not-accessible
			STATUS current
			DESCRIPTION
				"Description."
			::= { gOnuSrvInfo 24 }

		
--  1.3.6.1.4.1.37950.1.1.6.1.1.8.20.1
		-- 1.3.6.1.4.1.37950.1.1.6.1.1.8.24.1
		gOnuSrvCATVUniEntry OBJECT-TYPE
			SYNTAX GOnuSrvCATVUniEntry
			MAX-ACCESS not-accessible
			STATUS current
			DESCRIPTION
				"Description."
			INDEX { gUniPonInx, gUniOnuInx }
			::= { gOnuSrvCATVUniTable 1 }

		
		GOnuSrvCATVUniEntry ::=
			SEQUENCE { 
				gUniPonInx
					Integer32,
				gUniOnuInx
					Integer32,
				gUniInterface
					OCTET STRING,
				gUniAdminState
					INTEGER,
				gUniARC
					Integer32,
				gUniARCInterval
					Integer32,
				gUniPowerControl
					INTEGER
			 }

--  1.3.6.1.4.1.37950.1.1.6.1.1.8.20.1.1
		-- 1.3.6.1.4.1.37950.1.1.6.1.1.8.24.1.1
		gUniPonInx OBJECT-TYPE
			SYNTAX Integer32
			MAX-ACCESS read-write
			STATUS current
			DESCRIPTION
				"Description."
			::= { gOnuSrvCATVUniEntry 1 }

		
--  1.3.6.1.4.1.37950.1.1.6.1.1.8.20.1.2
		-- 1.3.6.1.4.1.37950.1.1.6.1.1.8.24.1.2
		gUniOnuInx OBJECT-TYPE
			SYNTAX Integer32
			MAX-ACCESS read-write
			STATUS current
			DESCRIPTION
				"Description."
			::= { gOnuSrvCATVUniEntry 2 }

		
--  1.3.6.1.4.1.37950.1.1.6.1.1.8.20.1.3
		-- 1.3.6.1.4.1.37950.1.1.6.1.1.8.24.1.3
		gUniInterface OBJECT-TYPE
			SYNTAX OCTET STRING
			MAX-ACCESS read-write
			STATUS current
			DESCRIPTION
				"Description."
			::= { gOnuSrvCATVUniEntry 3 }

		
--  1.3.6.1.4.1.37950.1.1.6.1.1.8.20.1.4
		-- 1.3.6.1.4.1.37950.1.1.6.1.1.8.24.1.4
		gUniAdminState OBJECT-TYPE
			SYNTAX INTEGER
				{
				unlock(1),
				lock(2)
				}
			MAX-ACCESS read-write
			STATUS current
			DESCRIPTION
				"Description."
			::= { gOnuSrvCATVUniEntry 4 }

		
--  1.3.6.1.4.1.37950.1.1.6.1.1.8.20.1.5
		-- 1.3.6.1.4.1.37950.1.1.6.1.1.8.24.1.5
		gUniARC OBJECT-TYPE
			SYNTAX Integer32
			MAX-ACCESS read-write
			STATUS current
			DESCRIPTION
				"Description."
			::= { gOnuSrvCATVUniEntry 5 }

		
--  1.3.6.1.4.1.37950.1.1.6.1.1.8.20.1.6
		-- 1.3.6.1.4.1.37950.1.1.6.1.1.8.24.1.6
		gUniARCInterval OBJECT-TYPE
			SYNTAX Integer32
			MAX-ACCESS read-write
			STATUS current
			DESCRIPTION
				"Description."
			::= { gOnuSrvCATVUniEntry 6 }

		
--  1.3.6.1.4.1.37950.1.1.6.1.1.8.20.1.7
		-- 1.3.6.1.4.1.37950.1.1.6.1.1.8.24.1.7
		gUniPowerControl OBJECT-TYPE
			SYNTAX INTEGER
				{
				disable(1),
				enable(2)
				}
			MAX-ACCESS read-write
			STATUS current
			DESCRIPTION
				"Description."
			::= { gOnuSrvCATVUniEntry 7 }

		
		-- 1.3.6.1.4.1.37950.1.1.6.1.1.8.25
		gOnuSrvCATVAniTable OBJECT-TYPE
			SYNTAX SEQUENCE OF GOnuSrvCATVAniEntry
			MAX-ACCESS not-accessible
			STATUS current
			DESCRIPTION
				"Description."
			::= { gOnuSrvInfo 25 }

		
		-- 1.3.6.1.4.1.37950.1.1.6.1.1.8.25.1
		gOnuSrvCATVAniEntry OBJECT-TYPE
			SYNTAX GOnuSrvCATVAniEntry
			MAX-ACCESS not-accessible
			STATUS current
			DESCRIPTION
				"Description."
			INDEX { gAniPonInx, gAniOnuInx }
			::= { gOnuSrvCATVAniTable 1 }

		
		GOnuSrvCATVAniEntry ::=
			SEQUENCE { 
				gAniPonInx
					Integer32,
				gAniOnuInx
					Integer32,
				gAniInterface
					OCTET STRING,
				gAniAdministrativeState
					OCTET STRING,
				gAniOperationState
					OCTET STRING,
				gAniARC
					Integer32,
				gAniARCInterval
					Integer32,
				gAniFrequencyRangeLow
					OCTET STRING,
				gAniFrequencyRangeHigh
					OCTET STRING,
				gAniSignalCapability
					OCTET STRING,
				gAniOpticalSignalLevel
					OCTET STRING,
				gAniPilotSignalLevel
					OCTET STRING,
				gAniSignalLevelMin
					OCTET STRING,
				gAniSignalLevelMax
					OCTET STRING,
				gAniPilotFrequency
					OCTET STRING,
				gAniAGCMode
					OCTET STRING,
				gAniAGCSetting
					OCTET STRING,
				gAniVideoLowerOpticalThreshold
					OCTET STRING,
				gAniVideoUpperOpticalThreshold
					OCTET STRING
			 }

		-- 1.3.6.1.4.1.37950.1.1.6.1.1.8.25.1.1
		gAniPonInx OBJECT-TYPE
			SYNTAX Integer32
			MAX-ACCESS read-write
			STATUS current
			DESCRIPTION
				"Description."
			::= { gOnuSrvCATVAniEntry 1 }

		
		-- 1.3.6.1.4.1.37950.1.1.6.1.1.8.25.1.2
		gAniOnuInx OBJECT-TYPE
			SYNTAX Integer32
			MAX-ACCESS read-write
			STATUS current
			DESCRIPTION
				"Description."
			::= { gOnuSrvCATVAniEntry 2 }

		
		-- 1.3.6.1.4.1.37950.1.1.6.1.1.8.25.1.3
		gAniInterface OBJECT-TYPE
			SYNTAX OCTET STRING
			MAX-ACCESS read-write
			STATUS current
			DESCRIPTION
				"Description."
			::= { gOnuSrvCATVAniEntry 3 }

		
		-- 1.3.6.1.4.1.37950.1.1.6.1.1.8.25.1.4
		gAniAdministrativeState OBJECT-TYPE
			SYNTAX OCTET STRING
			MAX-ACCESS read-write
			STATUS current
			DESCRIPTION
				"Description."
			::= { gOnuSrvCATVAniEntry 4 }

		
		-- 1.3.6.1.4.1.37950.1.1.6.1.1.8.25.1.5
		gAniOperationState OBJECT-TYPE
			SYNTAX OCTET STRING
			MAX-ACCESS read-write
			STATUS current
			DESCRIPTION
				"Description."
			::= { gOnuSrvCATVAniEntry 5 }

		
		-- 1.3.6.1.4.1.37950.1.1.6.1.1.8.25.1.6
		gAniARC OBJECT-TYPE
			SYNTAX Integer32
			MAX-ACCESS read-write
			STATUS current
			DESCRIPTION
				"Description."
			::= { gOnuSrvCATVAniEntry 6 }

		
		-- 1.3.6.1.4.1.37950.1.1.6.1.1.8.25.1.7
		gAniARCInterval OBJECT-TYPE
			SYNTAX Integer32
			MAX-ACCESS read-write
			STATUS current
			DESCRIPTION
				"Description."
			::= { gOnuSrvCATVAniEntry 7 }

		
		-- 1.3.6.1.4.1.37950.1.1.6.1.1.8.25.1.8
		gAniFrequencyRangeLow OBJECT-TYPE
			SYNTAX OCTET STRING
			MAX-ACCESS read-write
			STATUS current
			DESCRIPTION
				"Description."
			::= { gOnuSrvCATVAniEntry 8 }

		
		-- 1.3.6.1.4.1.37950.1.1.6.1.1.8.25.1.9
		gAniFrequencyRangeHigh OBJECT-TYPE
			SYNTAX OCTET STRING
			MAX-ACCESS read-write
			STATUS current
			DESCRIPTION
				"Description."
			::= { gOnuSrvCATVAniEntry 9 }

		
		-- 1.3.6.1.4.1.37950.1.1.6.1.1.8.25.1.10
		gAniSignalCapability OBJECT-TYPE
			SYNTAX OCTET STRING
			MAX-ACCESS read-write
			STATUS current
			DESCRIPTION
				"Description."
			::= { gOnuSrvCATVAniEntry 10 }

		
		-- 1.3.6.1.4.1.37950.1.1.6.1.1.8.25.1.11
		gAniOpticalSignalLevel OBJECT-TYPE
			SYNTAX OCTET STRING
			MAX-ACCESS read-write
			STATUS current
			DESCRIPTION
				"Description."
			::= { gOnuSrvCATVAniEntry 11 }

		
		-- 1.3.6.1.4.1.37950.1.1.6.1.1.8.25.1.12
		gAniPilotSignalLevel OBJECT-TYPE
			SYNTAX OCTET STRING
			MAX-ACCESS read-write
			STATUS current
			DESCRIPTION
				"Description."
			::= { gOnuSrvCATVAniEntry 12 }

		
		-- 1.3.6.1.4.1.37950.1.1.6.1.1.8.25.1.13
		gAniSignalLevelMin OBJECT-TYPE
			SYNTAX OCTET STRING
			MAX-ACCESS read-write
			STATUS current
			DESCRIPTION
				"Description."
			::= { gOnuSrvCATVAniEntry 13 }

		
		-- 1.3.6.1.4.1.37950.1.1.6.1.1.8.25.1.14
		gAniSignalLevelMax OBJECT-TYPE
			SYNTAX OCTET STRING
			MAX-ACCESS read-write
			STATUS current
			DESCRIPTION
				"Description."
			::= { gOnuSrvCATVAniEntry 14 }

		
		-- 1.3.6.1.4.1.37950.1.1.6.1.1.8.25.1.15
		gAniPilotFrequency OBJECT-TYPE
			SYNTAX OCTET STRING
			MAX-ACCESS read-write
			STATUS current
			DESCRIPTION
				"Description."
			::= { gOnuSrvCATVAniEntry 15 }

		
		-- 1.3.6.1.4.1.37950.1.1.6.1.1.8.25.1.16
		gAniAGCMode OBJECT-TYPE
			SYNTAX OCTET STRING
			MAX-ACCESS read-write
			STATUS current
			DESCRIPTION
				"Description."
			::= { gOnuSrvCATVAniEntry 16 }

		
		-- 1.3.6.1.4.1.37950.1.1.6.1.1.8.25.1.17
		gAniAGCSetting OBJECT-TYPE
			SYNTAX OCTET STRING
			MAX-ACCESS read-write
			STATUS current
			DESCRIPTION
				"Description."
			::= { gOnuSrvCATVAniEntry 17 }

		
		-- 1.3.6.1.4.1.37950.1.1.6.1.1.8.25.1.18
		gAniVideoLowerOpticalThreshold OBJECT-TYPE
			SYNTAX OCTET STRING
			MAX-ACCESS read-write
			STATUS current
			DESCRIPTION
				"Description."
			::= { gOnuSrvCATVAniEntry 18 }

		
		-- 1.3.6.1.4.1.37950.1.1.6.1.1.8.25.1.19
		gAniVideoUpperOpticalThreshold OBJECT-TYPE
			SYNTAX OCTET STRING
			MAX-ACCESS read-write
			STATUS current
			DESCRIPTION
				"Description."
			::= { gOnuSrvCATVAniEntry 19 }

		
--  1.3.6.1.4.1.37950.1.1.6.1.1.10
		-- 1.3.6.1.4.1.37950.1.1.6.1.1.10
		gOnuAuthModify OBJECT IDENTIFIER ::= { gOnuAuthList 10 }

		
--  1.3.6.1.4.1.37950.1.1.6.1.1.10.1
		-- 1.3.6.1.4.1.37950.1.1.6.1.1.10.1
		gOnuAuthPonInx OBJECT-TYPE
			SYNTAX Integer32 (1..16)
			MAX-ACCESS read-write
			STATUS current
			DESCRIPTION
				"Description."
			::= { gOnuAuthModify 1 }

		
--  1.3.6.1.4.1.37950.1.1.6.1.1.10.2
		-- 1.3.6.1.4.1.37950.1.1.6.1.1.10.2
		gOnuAuthOnuInx OBJECT-TYPE
			SYNTAX Integer32 (1..128)
			MAX-ACCESS read-write
			STATUS current
			DESCRIPTION
				"Description."
			::= { gOnuAuthModify 2 }

		
--  1.3.6.1.4.1.37950.1.1.6.1.1.10.3
		-- 1.3.6.1.4.1.37950.1.1.6.1.1.10.3
		gOnuAuthMode OBJECT-TYPE
			SYNTAX INTEGER
				{
				sn(1),
				loid(2)
				}
			MAX-ACCESS read-write
			STATUS current
			DESCRIPTION
				"Description."
			::= { gOnuAuthModify 3 }

		
--  1.3.6.1.4.1.37950.1.1.6.1.1.10.4
		-- 1.3.6.1.4.1.37950.1.1.6.1.1.10.4
		gOnuAuthInfo OBJECT-TYPE
			SYNTAX OCTET STRING
			MAX-ACCESS read-write
			STATUS current
			DESCRIPTION
				"Description."
			::= { gOnuAuthModify 4 }

		
--  1.3.6.1.4.1.37950.1.1.6.1.1.10.5
		-- 1.3.6.1.4.1.37950.1.1.6.1.1.10.5
		gOnuAuthAction OBJECT-TYPE
			SYNTAX INTEGER { commit(1) }
			MAX-ACCESS read-write
			STATUS current
			DESCRIPTION
				"Description."
			::= { gOnuAuthModify 5 }

		
--  1.3.6.1.4.1.37950.1.1.6.1.1.11
		-- 1.3.6.1.4.1.37950.1.1.6.1.1.11
		gOnuCapabilityTable OBJECT-TYPE
			SYNTAX SEQUENCE OF GOnuCapabilityEntry
			MAX-ACCESS not-accessible
			STATUS current
			DESCRIPTION
				"Description."
			::= { gOnuAuthList 11 }

		
--  1.3.6.1.4.1.37950.1.1.6.1.1.11.1
		-- 1.3.6.1.4.1.37950.1.1.6.1.1.11.1
		gOnuCapabilityEntry OBJECT-TYPE
			SYNTAX GOnuCapabilityEntry
			MAX-ACCESS not-accessible
			STATUS current
			DESCRIPTION
				"Description."
			INDEX { gOnuCapabilityPon, gOnuCapabilityOnu }
			::= { gOnuCapabilityTable 1 }

		
		GOnuCapabilityEntry ::=
			SEQUENCE { 
				gOnuCapabilityPon
					Integer32,
				gOnuCapabilityOnu
					Integer32,
				gOnuCapabilityTcontNum
					Integer32,
				gOnuCapabilityGemNum
					Integer32,
				gOnuCapabilityTpqNum
					Integer32,
				gOnuCapabilityUpqNum
					Integer32,
				gOnuCapabilityDpqNum
					Integer32,
				gOnuCapabilityTraNum
					Integer32,
				gOnuCapabilityOption
					OCTET STRING,
				gOnuCapabilityTUniNum
					Integer32,
				gOnuCapabilityEUniNum
					Integer32,
				gOnuCapability10GENum
					Integer32,
				gOnuCapabilityGENum
					Integer32,
				gOnuCapabilityFENum
					Integer32,
				gOnuCapabilityCESNum
					Integer32,
				gOnuCapabilityPOTSNum
					Integer32,
				gOnuCapabilityVideoNum
					Integer32,
				gOnuCapabilityWifiNum
					Integer32,
				gOnuCapabilityXDSLNum
					Integer32,
				gOnuCapabilityIPHostNum
					Integer32,
				gOnuCapabilityIPv6HostNum
					Integer32,
				gOnuCapabilityVeipNum
					Integer32,
				gOnuCapabilityOpId
					OCTET STRING,
				gOnuCapabilityCtcVer
					OCTET STRING,
				gOnuCapabilityCucVer
					OCTET STRING,
				gOnuCapabilityOnuType
					OCTET STRING,
				gOnuCapabilityTxControl
					OCTET STRING,
				gOnuCapability40GENum
					Integer32,
				gOnuCapability25GENum
					Integer32,
				gOnuCapability5GENum
					Integer32,
				gOnuCapabilityHalf5GENum
					Integer32,
				gOnuCapabilityViUniNum
					OCTET STRING
			 }

--  1.3.6.1.4.1.37950.1.1.6.1.1.11.1.1
		-- 1.3.6.1.4.1.37950.1.1.6.1.1.11.1.1
		gOnuCapabilityPon OBJECT-TYPE
			SYNTAX Integer32 (1..16)
			MAX-ACCESS read-only
			STATUS current
			DESCRIPTION
				"Description."
			::= { gOnuCapabilityEntry 1 }

		
--  1.3.6.1.4.1.37950.1.1.6.1.1.11.1.2
		-- 1.3.6.1.4.1.37950.1.1.6.1.1.11.1.2
		gOnuCapabilityOnu OBJECT-TYPE
			SYNTAX Integer32 (1..128)
			MAX-ACCESS read-only
			STATUS current
			DESCRIPTION
				"Description."
			::= { gOnuCapabilityEntry 2 }

		
--  1.3.6.1.4.1.37950.1.1.6.1.1.11.1.3
		-- 1.3.6.1.4.1.37950.1.1.6.1.1.11.1.3
		gOnuCapabilityTcontNum OBJECT-TYPE
			SYNTAX Integer32
			MAX-ACCESS read-only
			STATUS current
			DESCRIPTION
				"Description."
			::= { gOnuCapabilityEntry 3 }

		
--  1.3.6.1.4.1.37950.1.1.6.1.1.11.1.4
		-- 1.3.6.1.4.1.37950.1.1.6.1.1.11.1.4
		gOnuCapabilityGemNum OBJECT-TYPE
			SYNTAX Integer32
			MAX-ACCESS read-only
			STATUS current
			DESCRIPTION
				"Description."
			::= { gOnuCapabilityEntry 4 }

		
--  1.3.6.1.4.1.37950.1.1.6.1.1.11.1.5
		-- 1.3.6.1.4.1.37950.1.1.6.1.1.11.1.5
		gOnuCapabilityTpqNum OBJECT-TYPE
			SYNTAX Integer32
			MAX-ACCESS read-only
			STATUS current
			DESCRIPTION
				"Description."
			::= { gOnuCapabilityEntry 5 }

		
--  1.3.6.1.4.1.37950.1.1.6.1.1.11.1.6
		-- 1.3.6.1.4.1.37950.1.1.6.1.1.11.1.6
		gOnuCapabilityUpqNum OBJECT-TYPE
			SYNTAX Integer32
			MAX-ACCESS read-only
			STATUS current
			DESCRIPTION
				"Description."
			::= { gOnuCapabilityEntry 6 }

		
--  1.3.6.1.4.1.37950.1.1.6.1.1.11.1.7
		-- 1.3.6.1.4.1.37950.1.1.6.1.1.11.1.7
		gOnuCapabilityDpqNum OBJECT-TYPE
			SYNTAX Integer32
			MAX-ACCESS read-only
			STATUS current
			DESCRIPTION
				"Description."
			::= { gOnuCapabilityEntry 7 }

		
--  1.3.6.1.4.1.37950.1.1.6.1.1.11.1.8
		-- 1.3.6.1.4.1.37950.1.1.6.1.1.11.1.8
		gOnuCapabilityTraNum OBJECT-TYPE
			SYNTAX Integer32
			MAX-ACCESS read-only
			STATUS current
			DESCRIPTION
				"Description."
			::= { gOnuCapabilityEntry 8 }

		
--  1.3.6.1.4.1.37950.1.1.6.1.1.11.1.9
		-- 1.3.6.1.4.1.37950.1.1.6.1.1.11.1.9
		gOnuCapabilityOption OBJECT-TYPE
			SYNTAX OCTET STRING
			MAX-ACCESS read-only
			STATUS current
			DESCRIPTION
				"Description."
			::= { gOnuCapabilityEntry 9 }

		
--  1.3.6.1.4.1.37950.1.1.6.1.1.11.1.10
		-- 1.3.6.1.4.1.37950.1.1.6.1.1.11.1.10
		gOnuCapabilityTUniNum OBJECT-TYPE
			SYNTAX Integer32
			MAX-ACCESS read-only
			STATUS current
			DESCRIPTION
				"Description."
			::= { gOnuCapabilityEntry 10 }

		
--  1.3.6.1.4.1.37950.1.1.6.1.1.11.1.11
		-- 1.3.6.1.4.1.37950.1.1.6.1.1.11.1.11
		gOnuCapabilityEUniNum OBJECT-TYPE
			SYNTAX Integer32
			MAX-ACCESS read-only
			STATUS current
			DESCRIPTION
				"Description."
			::= { gOnuCapabilityEntry 11 }

		
--  1.3.6.1.4.1.37950.1.1.6.1.1.11.1.12
		-- 1.3.6.1.4.1.37950.1.1.6.1.1.11.1.12
		gOnuCapability10GENum OBJECT-TYPE
			SYNTAX Integer32
			MAX-ACCESS read-only
			STATUS current
			DESCRIPTION
				"Description."
			::= { gOnuCapabilityEntry 12 }

		
--  1.3.6.1.4.1.37950.1.1.6.1.1.11.1.13
		-- 1.3.6.1.4.1.37950.1.1.6.1.1.11.1.13
		gOnuCapabilityGENum OBJECT-TYPE
			SYNTAX Integer32
			MAX-ACCESS read-only
			STATUS current
			DESCRIPTION
				"Description."
			::= { gOnuCapabilityEntry 13 }

		
--  1.3.6.1.4.1.37950.1.1.6.1.1.11.1.14
		-- 1.3.6.1.4.1.37950.1.1.6.1.1.11.1.14
		gOnuCapabilityFENum OBJECT-TYPE
			SYNTAX Integer32
			MAX-ACCESS read-only
			STATUS current
			DESCRIPTION
				"Description."
			::= { gOnuCapabilityEntry 14 }

		
--  1.3.6.1.4.1.37950.1.1.6.1.1.11.1.15
		-- 1.3.6.1.4.1.37950.1.1.6.1.1.11.1.15
		gOnuCapabilityCESNum OBJECT-TYPE
			SYNTAX Integer32
			MAX-ACCESS read-only
			STATUS current
			DESCRIPTION
				"Description."
			::= { gOnuCapabilityEntry 15 }

		
--  1.3.6.1.4.1.37950.1.1.6.1.1.11.1.16
		-- 1.3.6.1.4.1.37950.1.1.6.1.1.11.1.16
		gOnuCapabilityPOTSNum OBJECT-TYPE
			SYNTAX Integer32
			MAX-ACCESS read-only
			STATUS current
			DESCRIPTION
				"Description."
			::= { gOnuCapabilityEntry 16 }

		
--  1.3.6.1.4.1.37950.1.1.6.1.1.11.1.17
		-- 1.3.6.1.4.1.37950.1.1.6.1.1.11.1.17
		gOnuCapabilityVideoNum OBJECT-TYPE
			SYNTAX Integer32
			MAX-ACCESS read-only
			STATUS current
			DESCRIPTION
				"Description."
			::= { gOnuCapabilityEntry 17 }

		
--  1.3.6.1.4.1.37950.1.1.6.1.1.11.1.18
		-- 1.3.6.1.4.1.37950.1.1.6.1.1.11.1.18
		gOnuCapabilityWifiNum OBJECT-TYPE
			SYNTAX Integer32
			MAX-ACCESS read-only
			STATUS current
			DESCRIPTION
				"Description."
			::= { gOnuCapabilityEntry 18 }

		
--  1.3.6.1.4.1.37950.1.1.6.1.1.11.1.19
		-- 1.3.6.1.4.1.37950.1.1.6.1.1.11.1.19
		gOnuCapabilityXDSLNum OBJECT-TYPE
			SYNTAX Integer32
			MAX-ACCESS read-only
			STATUS current
			DESCRIPTION
				"Description."
			::= { gOnuCapabilityEntry 19 }

		
--  1.3.6.1.4.1.37950.1.1.6.1.1.11.1.20
		-- 1.3.6.1.4.1.37950.1.1.6.1.1.11.1.20
		gOnuCapabilityIPHostNum OBJECT-TYPE
			SYNTAX Integer32
			MAX-ACCESS read-only
			STATUS current
			DESCRIPTION
				"Description."
			::= { gOnuCapabilityEntry 20 }

		
--  1.3.6.1.4.1.37950.1.1.6.1.1.11.1.21
		-- 1.3.6.1.4.1.37950.1.1.6.1.1.11.1.21
		gOnuCapabilityIPv6HostNum OBJECT-TYPE
			SYNTAX Integer32
			MAX-ACCESS read-only
			STATUS current
			DESCRIPTION
				"Description."
			::= { gOnuCapabilityEntry 21 }

		
--  1.3.6.1.4.1.37950.1.1.6.1.1.11.1.22
		-- 1.3.6.1.4.1.37950.1.1.6.1.1.11.1.22
		gOnuCapabilityVeipNum OBJECT-TYPE
			SYNTAX Integer32
			MAX-ACCESS read-only
			STATUS current
			DESCRIPTION
				"Description."
			::= { gOnuCapabilityEntry 22 }

		
--  1.3.6.1.4.1.37950.1.1.6.1.1.11.1.23
		-- 1.3.6.1.4.1.37950.1.1.6.1.1.11.1.23
		gOnuCapabilityOpId OBJECT-TYPE
			SYNTAX OCTET STRING
			MAX-ACCESS read-only
			STATUS current
			DESCRIPTION
				"Description."
			::= { gOnuCapabilityEntry 23 }

		
--  1.3.6.1.4.1.37950.1.1.6.1.1.11.1.24
		-- 1.3.6.1.4.1.37950.1.1.6.1.1.11.1.24
		gOnuCapabilityCtcVer OBJECT-TYPE
			SYNTAX OCTET STRING
			MAX-ACCESS read-only
			STATUS current
			DESCRIPTION
				"Description."
			::= { gOnuCapabilityEntry 24 }

		
--  1.3.6.1.4.1.37950.1.1.6.1.1.11.1.25
		-- 1.3.6.1.4.1.37950.1.1.6.1.1.11.1.25
		gOnuCapabilityCucVer OBJECT-TYPE
			SYNTAX OCTET STRING
			MAX-ACCESS read-only
			STATUS current
			DESCRIPTION
				"Description."
			::= { gOnuCapabilityEntry 25 }

		
--  1.3.6.1.4.1.37950.1.1.6.1.1.11.1.26
		-- 1.3.6.1.4.1.37950.1.1.6.1.1.11.1.26
		gOnuCapabilityOnuType OBJECT-TYPE
			SYNTAX OCTET STRING
			MAX-ACCESS read-only
			STATUS current
			DESCRIPTION
				"Description."
			::= { gOnuCapabilityEntry 26 }

		
--  1.3.6.1.4.1.37950.1.1.6.1.1.11.1.27
		-- 1.3.6.1.4.1.37950.1.1.6.1.1.11.1.27
		gOnuCapabilityTxControl OBJECT-TYPE
			SYNTAX OCTET STRING
			MAX-ACCESS read-only
			STATUS current
			DESCRIPTION
				"Description."
			::= { gOnuCapabilityEntry 27 }

		
--  1.3.6.1.4.1.37950.1.1.6.1.1.11.1.28
		-- 1.3.6.1.4.1.37950.1.1.6.1.1.11.1.28
		gOnuCapability40GENum OBJECT-TYPE
			SYNTAX Integer32
			MAX-ACCESS read-only
			STATUS current
			DESCRIPTION
				"Description."
			::= { gOnuCapabilityEntry 28 }

		
--  1.3.6.1.4.1.37950.1.1.6.1.1.11.1.29
		-- 1.3.6.1.4.1.37950.1.1.6.1.1.11.1.29
		gOnuCapability25GENum OBJECT-TYPE
			SYNTAX Integer32
			MAX-ACCESS read-only
			STATUS current
			DESCRIPTION
				"Description."
			::= { gOnuCapabilityEntry 29 }

		
--  1.3.6.1.4.1.37950.1.1.6.1.1.11.1.30
		-- 1.3.6.1.4.1.37950.1.1.6.1.1.11.1.30
		gOnuCapability5GENum OBJECT-TYPE
			SYNTAX Integer32
			MAX-ACCESS read-only
			STATUS current
			DESCRIPTION
				"Description."
			::= { gOnuCapabilityEntry 30 }

		
--  1.3.6.1.4.1.37950.1.1.6.1.1.11.1.31
		-- 1.3.6.1.4.1.37950.1.1.6.1.1.11.1.31
		gOnuCapabilityHalf5GENum OBJECT-TYPE
			SYNTAX Integer32
			MAX-ACCESS read-only
			STATUS current
			DESCRIPTION
				"Description."
			::= { gOnuCapabilityEntry 31 }

		
--  1.3.6.1.4.1.37950.1.1.6.1.1.11.1.32
		-- 1.3.6.1.4.1.37950.1.1.6.1.1.11.1.32
		gOnuCapabilityViUniNum OBJECT-TYPE
			SYNTAX OCTET STRING
			MAX-ACCESS read-only
			STATUS current
			DESCRIPTION
				"Description."
			::= { gOnuCapabilityEntry 32 }

		
--  1.3.6.1.4.1.37950.1.1.6.1.1.12
		-- 1.3.6.1.4.1.37950.1.1.6.1.1.12
		gOnuRttTable OBJECT-TYPE
			SYNTAX SEQUENCE OF GOnuRttEntry
			MAX-ACCESS not-accessible
			STATUS current
			DESCRIPTION
				"Description."
			::= { gOnuAuthList 12 }

		
--  1.3.6.1.4.1.37950.1.1.6.1.1.12.1
		-- 1.3.6.1.4.1.37950.1.1.6.1.1.12.1
		gOnuRttEntry OBJECT-TYPE
			SYNTAX GOnuRttEntry
			MAX-ACCESS not-accessible
			STATUS current
			DESCRIPTION
				"Description."
			INDEX { gOnuRttPon, gOnuRttOnu }
			::= { gOnuRttTable 1 }

		
		GOnuRttEntry ::=
			SEQUENCE { 
				gOnuRttPon
					INTEGER,
				gOnuRttOnu
					INTEGER,
				gOnuRttDistance
					INTEGER
			 }

--  1.3.6.1.4.1.37950.1.1.6.1.1.12.1.1
		-- 1.3.6.1.4.1.37950.1.1.6.1.1.12.1.1
		gOnuRttPon OBJECT-TYPE
			SYNTAX INTEGER (1..16)
			MAX-ACCESS read-only
			STATUS current
			DESCRIPTION
				"Description."
			::= { gOnuRttEntry 1 }

		
--  1.3.6.1.4.1.37950.1.1.6.1.1.12.1.2
		-- 1.3.6.1.4.1.37950.1.1.6.1.1.12.1.2
		gOnuRttOnu OBJECT-TYPE
			SYNTAX INTEGER (1..128)
			MAX-ACCESS read-only
			STATUS current
			DESCRIPTION
				"Description."
			::= { gOnuRttEntry 2 }

		
--  1.3.6.1.4.1.37950.1.1.6.1.1.12.1.3
		-- 1.3.6.1.4.1.37950.1.1.6.1.1.12.1.3
		gOnuRttDistance OBJECT-TYPE
			SYNTAX INTEGER
			MAX-ACCESS read-only
			STATUS current
			DESCRIPTION
				"Description."
			::= { gOnuRttEntry 3 }

		
--  1.3.6.1.4.1.37950.1.1.6.1.1.13
		-- 1.3.6.1.4.1.37950.1.1.6.1.1.13
		gOnuSearch OBJECT IDENTIFIER ::= { gOnuAuthList 13 }

		
--  1.3.6.1.4.1.37950.1.1.6.1.1.13.1
		-- 1.3.6.1.4.1.37950.1.1.6.1.1.13.1
		gOnuSearchMode OBJECT-TYPE
			SYNTAX INTEGER
				{
				sn(1),
				pw(2),
				loid(3)
				}
			MAX-ACCESS read-write
			STATUS current
			DESCRIPTION
				"Description."
			::= { gOnuSearch 1 }

		
--  1.3.6.1.4.1.37950.1.1.6.1.1.13.2
		-- 1.3.6.1.4.1.37950.1.1.6.1.1.13.2
		gOnuSearchKey OBJECT-TYPE
			SYNTAX OCTET STRING
			MAX-ACCESS read-write
			STATUS current
			DESCRIPTION
				"Description."
			::= { gOnuSearch 2 }

		
--  1.3.6.1.4.1.37950.1.1.6.1.1.13.3
		-- 1.3.6.1.4.1.37950.1.1.6.1.1.13.3
		gOnuSearchAction OBJECT-TYPE
			SYNTAX INTEGER { commit(1) }
			MAX-ACCESS read-write
			STATUS current
			DESCRIPTION
				"Description."
			::= { gOnuSearch 3 }

		
--  1.3.6.1.4.1.37950.1.1.6.1.1.14
		-- 1.3.6.1.4.1.37950.1.1.6.1.1.14
		gOnuSearchTable OBJECT-TYPE
			SYNTAX SEQUENCE OF GOnuSearchEntry
			MAX-ACCESS not-accessible
			STATUS current
			DESCRIPTION
				"Description."
			::= { gOnuAuthList 14 }

		
--  1.3.6.1.4.1.37950.1.1.6.1.1.14.1
		-- 1.3.6.1.4.1.37950.1.1.6.1.1.14.1
		gOnuSearchEntry OBJECT-TYPE
			SYNTAX GOnuSearchEntry
			MAX-ACCESS not-accessible
			STATUS current
			DESCRIPTION
				"Description."
			INDEX { gOnuSearchTPon, gOnuSearchTOnu }
			::= { gOnuSearchTable 1 }

		
		GOnuSearchEntry ::=
			SEQUENCE { 
				gOnuSearchTPon
					Integer32,
				gOnuSearchTOnu
					Integer32,
				gOnuSearchTMode
					INTEGER,
				gOnuSearchTkey
					OCTET STRING
			 }

--  1.3.6.1.4.1.37950.1.1.6.1.1.14.1.1
		-- 1.3.6.1.4.1.37950.1.1.6.1.1.14.1.1
		gOnuSearchTPon OBJECT-TYPE
			SYNTAX Integer32
			MAX-ACCESS read-only
			STATUS current
			DESCRIPTION
				"Description."
			::= { gOnuSearchEntry 1 }

		
--  1.3.6.1.4.1.37950.1.1.6.1.1.14.1.2
		-- 1.3.6.1.4.1.37950.1.1.6.1.1.14.1.2
		gOnuSearchTOnu OBJECT-TYPE
			SYNTAX Integer32
			MAX-ACCESS read-only
			STATUS current
			DESCRIPTION
				"Description."
			::= { gOnuSearchEntry 2 }

		
--  1.3.6.1.4.1.37950.1.1.6.1.1.14.1.3
		-- 1.3.6.1.4.1.37950.1.1.6.1.1.14.1.3
		gOnuSearchTMode OBJECT-TYPE
			SYNTAX INTEGER
				{
				sn(1),
				pw(2),
				loid(3)
				}
			MAX-ACCESS read-only
			STATUS current
			DESCRIPTION
				"Description."
			::= { gOnuSearchEntry 3 }

		
--  1.3.6.1.4.1.37950.1.1.6.1.1.14.1.4
		-- 1.3.6.1.4.1.37950.1.1.6.1.1.14.1.4
		gOnuSearchTkey OBJECT-TYPE
			SYNTAX OCTET STRING
			MAX-ACCESS read-only
			STATUS current
			DESCRIPTION
				"Description."
			::= { gOnuSearchEntry 4 }

		
--  1.3.6.1.4.1.37950.1.1.6.1.1.15
		-- 1.3.6.1.4.1.37950.1.1.6.1.1.15
		gOnuWhitelist OBJECT IDENTIFIER ::= { gOnuAuthList 15 }

		
--  1.3.6.1.4.1.37950.1.1.6.1.1.15.1
		-- 1.3.6.1.4.1.37950.1.1.6.1.1.15.1
		gOnuWhitelistsn OBJECT-TYPE
			SYNTAX OCTET STRING
			MAX-ACCESS read-write
			STATUS current
			DESCRIPTION
				"Description."
			::= { gOnuWhitelist 1 }

		
--  1.3.6.1.4.1.37950.1.1.6.1.1.15.2
		-- 1.3.6.1.4.1.37950.1.1.6.1.1.15.2
		gOnuWhitelistendsn OBJECT-TYPE
			SYNTAX OCTET STRING
			MAX-ACCESS read-write
			STATUS current
			DESCRIPTION
				"Description."
			::= { gOnuWhitelist 2 }

		
--  1.3.6.1.4.1.37950.1.1.6.1.1.15.3
		-- 1.3.6.1.4.1.37950.1.1.6.1.1.15.3
		gOnuWhitelistaction OBJECT-TYPE
			SYNTAX INTEGER
				{
				add(0),
				del(1),
				clear(2)
				}
			MAX-ACCESS read-write
			STATUS current
			DESCRIPTION
				"Description."
			::= { gOnuWhitelist 3 }

		
--  1.3.6.1.4.1.37950.1.1.6.1.1.16
		-- 1.3.6.1.4.1.37950.1.1.6.1.1.16
		gOnuWhitelistTable OBJECT-TYPE
			SYNTAX SEQUENCE OF GOnuWhitelistEntry
			MAX-ACCESS not-accessible
			STATUS current
			DESCRIPTION
				"Description."
			::= { gOnuAuthList 16 }

		
--  1.3.6.1.4.1.37950.1.1.6.1.1.16.1
		-- 1.3.6.1.4.1.37950.1.1.6.1.1.16.1
		gOnuWhitelistEntry OBJECT-TYPE
			SYNTAX GOnuWhitelistEntry
			MAX-ACCESS not-accessible
			STATUS current
			DESCRIPTION
				"Description."
			INDEX { gOnuWhitelistIndex }
			::= { gOnuWhitelistTable 1 }

		
		GOnuWhitelistEntry ::=
			SEQUENCE { 
				gOnuWhitelistIndex
					Integer32,
				gOnuWhitelistsnS
					OCTET STRING,
				gOnuWhitelistendsnS
					OCTET STRING
			 }

--  1.3.6.1.4.1.37950.1.1.6.1.1.16.1.1
		-- 1.3.6.1.4.1.37950.1.1.6.1.1.16.1.1
		gOnuWhitelistIndex OBJECT-TYPE
			SYNTAX Integer32
			MAX-ACCESS read-write
			STATUS current
			DESCRIPTION
				"Description."
			::= { gOnuWhitelistEntry 1 }

		
--  1.3.6.1.4.1.37950.1.1.6.1.1.16.1.2
		-- 1.3.6.1.4.1.37950.1.1.6.1.1.16.1.2
		gOnuWhitelistsnS OBJECT-TYPE
			SYNTAX OCTET STRING
			MAX-ACCESS read-write
			STATUS current
			DESCRIPTION
				"Description."
			::= { gOnuWhitelistEntry 2 }

		
--  1.3.6.1.4.1.37950.1.1.6.1.1.16.1.3
		-- 1.3.6.1.4.1.37950.1.1.6.1.1.16.1.3
		gOnuWhitelistendsnS OBJECT-TYPE
			SYNTAX OCTET STRING
			MAX-ACCESS read-write
			STATUS current
			DESCRIPTION
				"Description."
			::= { gOnuWhitelistEntry 3 }

		
--  1.3.6.1.4.1.37950.1.1.6.1.1.17
		-- 1.3.6.1.4.1.37950.1.1.6.1.1.17
		gOnuStaTable OBJECT-TYPE
			SYNTAX SEQUENCE OF GOnuStaEntry
			MAX-ACCESS not-accessible
			STATUS current
			DESCRIPTION
				"Description."
			::= { gOnuAuthList 17 }

		
--  1.3.6.1.4.1.37950.1.1.6.1.1.17.1
		-- 1.3.6.1.4.1.37950.1.1.6.1.1.17.1
		gOnuStaEntry OBJECT-TYPE
			SYNTAX GOnuStaEntry
			MAX-ACCESS not-accessible
			STATUS current
			DESCRIPTION
				"Description."
			INDEX { gOnuStaPonInx, gOnuStaOnuInx }
			::= { gOnuStaTable 1 }

		
		GOnuStaEntry ::=
			SEQUENCE { 
				gOnuStaPonInx
					INTEGER,
				gOnuStaOnuInx
					INTEGER,
				gOnuStaInputRateBps
					Integer32,
				gOnuStaInputRatePps
					Integer32,
				gOnuStaOutputRateBps
					Integer32,
				gOnuStaOutputRatePps
					Integer32,
				gOnuStaInputBandThoughput
					OCTET STRING,
				gOnuStaOutputBandThoughput
					OCTET STRING,
				gOnuStaInputPeakRateBps
					Integer32,
				gOnuStaInputPeakRatePps
					Integer32,
				gOnuStaOutputPeakRateBps
					Integer32,
				gOnuStaOutputPeakRatePps
					Integer32,
				gOnuStaInputOctets
					Counter64,
				gOnuStaInputPackets
					Counter64,
				gOnuStaOutputOctets
					Counter64,
				gOnuStaOutputPackets
					Counter64
			 }

--  1.3.6.1.4.1.37950.1.1.6.1.1.17.1.1
		-- 1.3.6.1.4.1.37950.1.1.6.1.1.17.1.1
		gOnuStaPonInx OBJECT-TYPE
			SYNTAX INTEGER (1..16)
			MAX-ACCESS read-only
			STATUS current
			DESCRIPTION
				"Description."
			::= { gOnuStaEntry 1 }

		
--  1.3.6.1.4.1.37950.1.1.6.1.1.17.1.2
		-- 1.3.6.1.4.1.37950.1.1.6.1.1.17.1.2
		gOnuStaOnuInx OBJECT-TYPE
			SYNTAX INTEGER (1..128)
			MAX-ACCESS read-only
			STATUS current
			DESCRIPTION
				"Description."
			::= { gOnuStaEntry 2 }

		
--  1.3.6.1.4.1.37950.1.1.6.1.1.17.1.3
		-- 1.3.6.1.4.1.37950.1.1.6.1.1.17.1.3
		gOnuStaInputRateBps OBJECT-TYPE
			SYNTAX Integer32
			MAX-ACCESS read-only
			STATUS current
			DESCRIPTION
				"Description."
			::= { gOnuStaEntry 3 }

		
--  1.3.6.1.4.1.37950.1.1.6.1.1.17.1.4
		-- 1.3.6.1.4.1.37950.1.1.6.1.1.17.1.4
		gOnuStaInputRatePps OBJECT-TYPE
			SYNTAX Integer32
			MAX-ACCESS read-only
			STATUS current
			DESCRIPTION
				"Description."
			::= { gOnuStaEntry 4 }

		
--  1.3.6.1.4.1.37950.1.1.6.1.1.17.1.5
		-- 1.3.6.1.4.1.37950.1.1.6.1.1.17.1.5
		gOnuStaOutputRateBps OBJECT-TYPE
			SYNTAX Integer32
			MAX-ACCESS read-only
			STATUS current
			DESCRIPTION
				"Description."
			::= { gOnuStaEntry 5 }

		
--  1.3.6.1.4.1.37950.1.1.6.1.1.17.1.6
		-- 1.3.6.1.4.1.37950.1.1.6.1.1.17.1.6
		gOnuStaOutputRatePps OBJECT-TYPE
			SYNTAX Integer32
			MAX-ACCESS read-only
			STATUS current
			DESCRIPTION
				"Description."
			::= { gOnuStaEntry 6 }

		
--  1.3.6.1.4.1.37950.1.1.6.1.1.17.1.7
		-- 1.3.6.1.4.1.37950.1.1.6.1.1.17.1.7
		gOnuStaInputBandThoughput OBJECT-TYPE
			SYNTAX OCTET STRING
			MAX-ACCESS read-only
			STATUS current
			DESCRIPTION
				"Description."
			::= { gOnuStaEntry 7 }

		
--  1.3.6.1.4.1.37950.1.1.6.1.1.17.1.8
		-- 1.3.6.1.4.1.37950.1.1.6.1.1.17.1.8
		gOnuStaOutputBandThoughput OBJECT-TYPE
			SYNTAX OCTET STRING
			MAX-ACCESS read-write
			STATUS current
			DESCRIPTION
				"Description."
			::= { gOnuStaEntry 8 }

		
--  1.3.6.1.4.1.37950.1.1.6.1.1.17.1.9
		-- 1.3.6.1.4.1.37950.1.1.6.1.1.17.1.9
		gOnuStaInputPeakRateBps OBJECT-TYPE
			SYNTAX Integer32
			MAX-ACCESS read-only
			STATUS current
			DESCRIPTION
				"Description."
			::= { gOnuStaEntry 9 }

		
--  1.3.6.1.4.1.37950.1.1.6.1.1.17.1.10
		-- 1.3.6.1.4.1.37950.1.1.6.1.1.17.1.10
		gOnuStaInputPeakRatePps OBJECT-TYPE
			SYNTAX Integer32
			MAX-ACCESS read-only
			STATUS current
			DESCRIPTION
				"Description."
			::= { gOnuStaEntry 10 }

		
--  1.3.6.1.4.1.37950.1.1.6.1.1.17.1.11
		-- 1.3.6.1.4.1.37950.1.1.6.1.1.17.1.11
		gOnuStaOutputPeakRateBps OBJECT-TYPE
			SYNTAX Integer32
			MAX-ACCESS read-only
			STATUS current
			DESCRIPTION
				"Description."
			::= { gOnuStaEntry 11 }

		
--  1.3.6.1.4.1.37950.1.1.6.1.1.17.1.12
		-- 1.3.6.1.4.1.37950.1.1.6.1.1.17.1.12
		gOnuStaOutputPeakRatePps OBJECT-TYPE
			SYNTAX Integer32
			MAX-ACCESS read-only
			STATUS current
			DESCRIPTION
				"Description."
			::= { gOnuStaEntry 12 }

		
--  1.3.6.1.4.1.37950.1.1.6.1.1.17.1.13
		-- 1.3.6.1.4.1.37950.1.1.6.1.1.17.1.13
		gOnuStaInputOctets OBJECT-TYPE
			SYNTAX Counter64
			MAX-ACCESS read-only
			STATUS current
			DESCRIPTION
				"Description."
			::= { gOnuStaEntry 13 }

		
--  1.3.6.1.4.1.37950.1.1.6.1.1.17.1.14
		-- 1.3.6.1.4.1.37950.1.1.6.1.1.17.1.14
		gOnuStaInputPackets OBJECT-TYPE
			SYNTAX Counter64
			MAX-ACCESS read-only
			STATUS current
			DESCRIPTION
				"Description."
			::= { gOnuStaEntry 14 }

		
--  1.3.6.1.4.1.37950.1.1.6.1.1.17.1.15
		-- 1.3.6.1.4.1.37950.1.1.6.1.1.17.1.15
		gOnuStaOutputOctets OBJECT-TYPE
			SYNTAX Counter64
			MAX-ACCESS read-only
			STATUS current
			DESCRIPTION
				"Description."
			::= { gOnuStaEntry 15 }

		
--  1.3.6.1.4.1.37950.1.1.6.1.1.17.1.16
		-- 1.3.6.1.4.1.37950.1.1.6.1.1.17.1.16
		gOnuStaOutputPackets OBJECT-TYPE
			SYNTAX Counter64
			MAX-ACCESS read-only
			STATUS current
			DESCRIPTION
				"Description."
			::= { gOnuStaEntry 16 }

		
--  1.3.6.1.4.1.37950.1.1.6.1.1.18
		-- 1.3.6.1.4.1.37950.1.1.6.1.1.18
		gOnuNumberTable OBJECT-TYPE
			SYNTAX SEQUENCE OF GOnuNumberEntry
			MAX-ACCESS not-accessible
			STATUS current
			DESCRIPTION
				"Description."
			::= { gOnuAuthList 18 }

		
--  1.3.6.1.4.1.37950.1.1.6.1.1.18.1
		-- 1.3.6.1.4.1.37950.1.1.6.1.1.18.1
		gOnuNumberEntry OBJECT-TYPE
			SYNTAX GOnuNumberEntry
			MAX-ACCESS not-accessible
			STATUS current
			DESCRIPTION
				"Description."
			INDEX { gOnuNumberPon }
			::= { gOnuNumberTable 1 }

		
		GOnuNumberEntry ::=
			SEQUENCE { 
				gOnuNumberPon
					Integer32,
				gOnuNumberAll
					Integer32,
				gOnuNumberOnline
					Integer32
			 }

--  1.3.6.1.4.1.37950.1.1.6.1.1.18.1.1
		-- 1.3.6.1.4.1.37950.1.1.6.1.1.18.1.1
		gOnuNumberPon OBJECT-TYPE
			SYNTAX Integer32
			MAX-ACCESS read-only
			STATUS current
			DESCRIPTION
				"Description."
			::= { gOnuNumberEntry 1 }

		
--  1.3.6.1.4.1.37950.1.1.6.1.1.18.1.2
		-- 1.3.6.1.4.1.37950.1.1.6.1.1.18.1.2
		gOnuNumberAll OBJECT-TYPE
			SYNTAX Integer32
			MAX-ACCESS read-only
			STATUS current
			DESCRIPTION
				"Description."
			::= { gOnuNumberEntry 2 }

		
--  1.3.6.1.4.1.37950.1.1.6.1.1.18.1.3
		-- 1.3.6.1.4.1.37950.1.1.6.1.1.18.1.3
		gOnuNumberOnline OBJECT-TYPE
			SYNTAX Integer32
			MAX-ACCESS read-only
			STATUS current
			DESCRIPTION
				"Description."
			::= { gOnuNumberEntry 3 }

		
--  1.3.6.1.4.1.37950.1.1.6.1.1.19
		-- 1.3.6.1.4.1.37950.1.1.6.1.1.19
		gOnuAuthInfo3Table OBJECT IDENTIFIER ::= { gOnuAuthList 19 }

		
--  1.3.6.1.4.1.37950.1.1.6.1.1.19.1
		-- 1.3.6.1.4.1.37950.1.1.6.1.1.19.1
		onuAuthInfo3Table OBJECT-TYPE
			SYNTAX SEQUENCE OF OnuAuthInfo3Entry
			MAX-ACCESS not-accessible
			STATUS current
			DESCRIPTION
				"Description."
			::= { gOnuAuthInfo3Table 1 }

		
--  1.3.6.1.4.1.37950.1.1.6.1.1.19.1.1
		-- 1.3.6.1.4.1.37950.1.1.6.1.1.19.1.1
		onuAuthInfo3Entry OBJECT-TYPE
			SYNTAX OnuAuthInfo3Entry
			MAX-ACCESS not-accessible
			STATUS current
			DESCRIPTION
				"Description."
			INDEX { authInfoPonNo3, authInfoOnuNo3 }
			::= { onuAuthInfo3Table 1 }

		
		OnuAuthInfo3Entry ::=
			SEQUENCE { 
				authInfoPonNo3
					Integer32,
				authInfoOnuNo3
					Integer32,
				onuAuthInfo3Details
					OCTET STRING
			 }

--  1.3.6.1.4.1.37950.1.1.6.1.1.19.1.1.1
		-- 1.3.6.1.4.1.37950.1.1.6.1.1.19.1.1.1
		authInfoPonNo3 OBJECT-TYPE
			SYNTAX Integer32
			MAX-ACCESS read-write
			STATUS current
			DESCRIPTION
				"Description."
			::= { onuAuthInfo3Entry 1 }

		
--  1.3.6.1.4.1.37950.1.1.6.1.1.19.1.1.2
		-- 1.3.6.1.4.1.37950.1.1.6.1.1.19.1.1.2
		authInfoOnuNo3 OBJECT-TYPE
			SYNTAX Integer32
			MAX-ACCESS read-write
			STATUS current
			DESCRIPTION
				"Description."
			::= { onuAuthInfo3Entry 2 }

		
--  1.3.6.1.4.1.37950.1.1.6.1.1.19.1.1.3
		-- 1.3.6.1.4.1.37950.1.1.6.1.1.19.1.1.3
		onuAuthInfo3Details OBJECT-TYPE
			SYNTAX OCTET STRING
			MAX-ACCESS read-write
			STATUS current
			DESCRIPTION
				"Description."
			::= { onuAuthInfo3Entry 3 }

		
--  1.3.6.1.4.1.37950.1.1.6.1.1.19.2
		-- 1.3.6.1.4.1.37950.1.1.6.1.1.19.2
		onlineOnuAuthInfo3Table OBJECT-TYPE
			SYNTAX SEQUENCE OF OnlineOnuAuthInfo3Entry
			MAX-ACCESS not-accessible
			STATUS current
			DESCRIPTION
				"Description."
			::= { gOnuAuthInfo3Table 2 }

		
--  1.3.6.1.4.1.37950.1.1.6.1.1.19.2.1
		-- 1.3.6.1.4.1.37950.1.1.6.1.1.19.2.1
		onlineOnuAuthInfo3Entry OBJECT-TYPE
			SYNTAX OnlineOnuAuthInfo3Entry
			MAX-ACCESS not-accessible
			STATUS current
			DESCRIPTION
				"Description."
			INDEX { onlineOnuAuthInfoPonNo3, onlineOnuAuthInfoOnuNo3 }
			::= { onlineOnuAuthInfo3Table 1 }

		
		OnlineOnuAuthInfo3Entry ::=
			SEQUENCE { 
				onlineOnuAuthInfoPonNo3
					Integer32,
				onlineOnuAuthInfoOnuNo3
					Integer32,
				onlineOnuAuthInfo3Details
					OCTET STRING
			 }

--  1.3.6.1.4.1.37950.1.1.6.1.1.19.2.1.1
		-- 1.3.6.1.4.1.37950.1.1.6.1.1.19.2.1.1
		onlineOnuAuthInfoPonNo3 OBJECT-TYPE
			SYNTAX Integer32
			MAX-ACCESS read-write
			STATUS current
			DESCRIPTION
				"Description."
			::= { onlineOnuAuthInfo3Entry 1 }

		
--  1.3.6.1.4.1.37950.1.1.6.1.1.19.2.1.2
		-- 1.3.6.1.4.1.37950.1.1.6.1.1.19.2.1.2
		onlineOnuAuthInfoOnuNo3 OBJECT-TYPE
			SYNTAX Integer32
			MAX-ACCESS read-write
			STATUS current
			DESCRIPTION
				"Description."
			::= { onlineOnuAuthInfo3Entry 2 }

		
--  1.3.6.1.4.1.37950.1.1.6.1.1.19.2.1.3
		-- 1.3.6.1.4.1.37950.1.1.6.1.1.19.2.1.3
		onlineOnuAuthInfo3Details OBJECT-TYPE
			SYNTAX OCTET STRING
			MAX-ACCESS read-write
			STATUS current
			DESCRIPTION
				"Description."
			::= { onlineOnuAuthInfo3Entry 3 }

		
--  1.3.6.1.4.1.37950.1.1.6.1.1.20
		-- 1.3.6.1.4.1.37950.1.1.6.1.1.20
		gOnuVersionTable OBJECT-TYPE
			SYNTAX SEQUENCE OF GOnuVersionEntry
			MAX-ACCESS not-accessible
			STATUS current
			DESCRIPTION
				"Description."
			::= { gOnuAuthList 20 }

		
--  1.3.6.1.4.1.37950.1.1.6.1.1.20.1
		-- 1.3.6.1.4.1.37950.1.1.6.1.1.20.1
		gOnuVersionEntry OBJECT-TYPE
			SYNTAX GOnuVersionEntry
			MAX-ACCESS not-accessible
			STATUS current
			DESCRIPTION
				"Description."
			INDEX { gOnuVerPonInx, gOnuVerOnuInx }
			::= { gOnuVersionTable 1 }

		
		GOnuVersionEntry ::=
			SEQUENCE { 
				gOnuVerPonInx
					INTEGER,
				gOnuVerOnuInx
					INTEGER,
				gOnuVerMainVer
					OCTET STRING,
				gOnuVerStandbyVer
					OCTET STRING,
				gOnuVerVersion
					OCTET STRING
			 }

--  1.3.6.1.4.1.37950.1.1.6.1.1.20.1.1
		-- 1.3.6.1.4.1.37950.1.1.6.1.1.20.1.1
		gOnuVerPonInx OBJECT-TYPE
			SYNTAX INTEGER
			MAX-ACCESS read-write
			STATUS current
			DESCRIPTION
				"Description."
			::= { gOnuVersionEntry 1 }

		
--  1.3.6.1.4.1.37950.1.1.6.1.1.20.1.2
		-- 1.3.6.1.4.1.37950.1.1.6.1.1.20.1.2
		gOnuVerOnuInx OBJECT-TYPE
			SYNTAX INTEGER
			MAX-ACCESS read-write
			STATUS current
			DESCRIPTION
				"Description."
			::= { gOnuVersionEntry 2 }

		
--  1.3.6.1.4.1.37950.1.1.6.1.1.20.1.3
		-- 1.3.6.1.4.1.37950.1.1.6.1.1.20.1.3
		gOnuVerMainVer OBJECT-TYPE
			SYNTAX OCTET STRING
			MAX-ACCESS read-write
			STATUS current
			DESCRIPTION
				"Description."
			::= { gOnuVersionEntry 3 }

		
--  1.3.6.1.4.1.37950.1.1.6.1.1.20.1.4
		-- 1.3.6.1.4.1.37950.1.1.6.1.1.20.1.4
		gOnuVerStandbyVer OBJECT-TYPE
			SYNTAX OCTET STRING
			MAX-ACCESS read-write
			STATUS current
			DESCRIPTION
				"Description."
			::= { gOnuVersionEntry 4 }

		
--  1.3.6.1.4.1.37950.1.1.6.1.1.20.1.5
		-- 1.3.6.1.4.1.37950.1.1.6.1.1.20.1.5
		gOnuVerVersion OBJECT-TYPE
			SYNTAX OCTET STRING
			MAX-ACCESS read-write
			STATUS current
			DESCRIPTION
				"Description."
			::= { gOnuVersionEntry 5 }

		
--  1.3.6.1.4.1.37950.1.1.6.1.1.21
		-- 1.3.6.1.4.1.37950.1.1.6.1.1.21
		gOnuPreConfig OBJECT IDENTIFIER ::= { gOnuAuthList 21 }

		
--  1.3.6.1.4.1.37950.1.1.6.1.1.21.1
		-- 1.3.6.1.4.1.37950.1.1.6.1.1.21.1
		gOnuPreConfigPON OBJECT-TYPE
			SYNTAX Integer32
			MAX-ACCESS read-write
			STATUS current
			DESCRIPTION
				"Description."
			::= { gOnuPreConfig 1 }

		
--  1.3.6.1.4.1.37950.1.1.6.1.1.21.2
		-- 1.3.6.1.4.1.37950.1.1.6.1.1.21.2
		gOnuPreConfigONU OBJECT-TYPE
			SYNTAX OCTET STRING
			MAX-ACCESS read-write
			STATUS current
			DESCRIPTION
				"Description."
			::= { gOnuPreConfig 2 }

		
--  1.3.6.1.4.1.37950.1.1.6.1.1.21.3
		-- 1.3.6.1.4.1.37950.1.1.6.1.1.21.3
		gOnuPreConfigONUProfile OBJECT-TYPE
			SYNTAX OCTET STRING
			MAX-ACCESS read-write
			STATUS current
			DESCRIPTION
				"Description."
			::= { gOnuPreConfig 3 }

		
--  1.3.6.1.4.1.37950.1.1.6.1.1.21.4
		-- 1.3.6.1.4.1.37950.1.1.6.1.1.21.4
		gOnuPreConfigLineProfile OBJECT-TYPE
			SYNTAX OCTET STRING
			MAX-ACCESS read-write
			STATUS current
			DESCRIPTION
				"Description."
			::= { gOnuPreConfig 4 }

		
--  1.3.6.1.4.1.37950.1.1.6.1.1.21.5
		-- 1.3.6.1.4.1.37950.1.1.6.1.1.21.5
		gOnuPreConfigSrvProfile OBJECT-TYPE
			SYNTAX OCTET STRING
			MAX-ACCESS read-write
			STATUS current
			DESCRIPTION
				"Description."
			::= { gOnuPreConfig 5 }

		
--  1.3.6.1.4.1.37950.1.1.6.1.1.21.6
		-- 1.3.6.1.4.1.37950.1.1.6.1.1.21.6
		gOnuPreConfigAlarmProfile OBJECT-TYPE
			SYNTAX OCTET STRING
			MAX-ACCESS read-write
			STATUS current
			DESCRIPTION
				"Description."
			::= { gOnuPreConfig 6 }

		
--  1.3.6.1.4.1.37950.1.1.6.1.1.21.7
		-- 1.3.6.1.4.1.37950.1.1.6.1.1.21.7
		gOnuPreConfigPriProfile OBJECT-TYPE
			SYNTAX OCTET STRING
			MAX-ACCESS read-write
			STATUS current
			DESCRIPTION
				"Description."
			::= { gOnuPreConfig 7 }

		
--  1.3.6.1.4.1.37950.1.1.6.1.1.21.8
		-- 1.3.6.1.4.1.37950.1.1.6.1.1.21.8
		gOnuPreConfigFormatProfile OBJECT-TYPE
			SYNTAX OCTET STRING
			MAX-ACCESS read-write
			STATUS current
			DESCRIPTION
				"Description."
			::= { gOnuPreConfig 8 }

		
--  1.3.6.1.4.1.37950.1.1.6.1.1.21.9
		-- 1.3.6.1.4.1.37950.1.1.6.1.1.21.9
		gOnuPreConfigAction OBJECT-TYPE
			SYNTAX INTEGER
				{
				add(0),
				delete(2),
				clear(3)
				}
			MAX-ACCESS read-write
			STATUS current
			DESCRIPTION
				"Description."
			::= { gOnuPreConfig 9 }

		
--  1.3.6.1.4.1.37950.1.1.6.1.1.22
		-- 1.3.6.1.4.1.37950.1.1.6.1.1.22
		gOnuPreConfigTable OBJECT-TYPE
			SYNTAX SEQUENCE OF GOnuPreConfigEntry
			MAX-ACCESS not-accessible
			STATUS current
			DESCRIPTION
				"Description."
			::= { gOnuAuthList 22 }

		
--  1.3.6.1.4.1.37950.1.1.6.1.1.22.1
		-- 1.3.6.1.4.1.37950.1.1.6.1.1.22.1
		gOnuPreConfigEntry OBJECT-TYPE
			SYNTAX GOnuPreConfigEntry
			MAX-ACCESS not-accessible
			STATUS current
			DESCRIPTION
				"Description."
			INDEX { gOnuPreConfigPONS, gOnuPreConfigONUS }
			::= { gOnuPreConfigTable 1 }

		
		GOnuPreConfigEntry ::=
			SEQUENCE { 
				gOnuPreConfigPONS
					Integer32,
				gOnuPreConfigONUS
					Integer32,
				gOnuPreConfigONUProfileS
					OCTET STRING,
				gOnuPreConfigLineProfileS
					OCTET STRING,
				gOnuPreConfigSrvProfileS
					OCTET STRING,
				gOnuPreConfigAlarmProfileS
					OCTET STRING,
				gOnuPreConfigPriProfileS
					OCTET STRING,
				gOnuPreConfigFormatProfileS
					OCTET STRING
			 }

--  1.3.6.1.4.1.37950.1.1.6.1.1.22.1.1
		-- 1.3.6.1.4.1.37950.1.1.6.1.1.22.1.1
		gOnuPreConfigPONS OBJECT-TYPE
			SYNTAX Integer32
			MAX-ACCESS read-write
			STATUS current
			DESCRIPTION
				"Description."
			::= { gOnuPreConfigEntry 1 }

		
--  1.3.6.1.4.1.37950.1.1.6.1.1.22.1.2
		-- 1.3.6.1.4.1.37950.1.1.6.1.1.22.1.2
		gOnuPreConfigONUS OBJECT-TYPE
			SYNTAX Integer32
			MAX-ACCESS read-write
			STATUS current
			DESCRIPTION
				"Description."
			::= { gOnuPreConfigEntry 2 }

		
--  1.3.6.1.4.1.37950.1.1.6.1.1.22.1.3
		-- 1.3.6.1.4.1.37950.1.1.6.1.1.22.1.3
		gOnuPreConfigONUProfileS OBJECT-TYPE
			SYNTAX OCTET STRING
			MAX-ACCESS read-write
			STATUS current
			DESCRIPTION
				"Description."
			::= { gOnuPreConfigEntry 3 }

		
--  1.3.6.1.4.1.37950.1.1.6.1.1.22.1.4
		-- 1.3.6.1.4.1.37950.1.1.6.1.1.22.1.4
		gOnuPreConfigLineProfileS OBJECT-TYPE
			SYNTAX OCTET STRING
			MAX-ACCESS read-write
			STATUS current
			DESCRIPTION
				"Description."
			::= { gOnuPreConfigEntry 4 }

		
--  1.3.6.1.4.1.37950.1.1.6.1.1.22.1.5
		-- 1.3.6.1.4.1.37950.1.1.6.1.1.22.1.5
		gOnuPreConfigSrvProfileS OBJECT-TYPE
			SYNTAX OCTET STRING
			MAX-ACCESS read-write
			STATUS current
			DESCRIPTION
				"Description."
			::= { gOnuPreConfigEntry 5 }

		
--  1.3.6.1.4.1.37950.1.1.6.1.1.22.1.6
		-- 1.3.6.1.4.1.37950.1.1.6.1.1.22.1.6
		gOnuPreConfigAlarmProfileS OBJECT-TYPE
			SYNTAX OCTET STRING
			MAX-ACCESS read-write
			STATUS current
			DESCRIPTION
				"Description."
			::= { gOnuPreConfigEntry 6 }

		
--  1.3.6.1.4.1.37950.1.1.6.1.1.22.1.7
		-- 1.3.6.1.4.1.37950.1.1.6.1.1.22.1.7
		gOnuPreConfigPriProfileS OBJECT-TYPE
			SYNTAX OCTET STRING
			MAX-ACCESS read-write
			STATUS current
			DESCRIPTION
				"Description."
			::= { gOnuPreConfigEntry 7 }

		
--  1.3.6.1.4.1.37950.1.1.6.1.1.22.1.8
		-- 1.3.6.1.4.1.37950.1.1.6.1.1.22.1.8
		gOnuPreConfigFormatProfileS OBJECT-TYPE
			SYNTAX OCTET STRING
			MAX-ACCESS read-write
			STATUS current
			DESCRIPTION
				"Description."
			::= { gOnuPreConfigEntry 8 }

		
--  1.3.6.1.4.1.37950.1.1.6.1.1.23
		-- 1.3.6.1.4.1.37950.1.1.6.1.1.23
		gOnuDerInfoTable OBJECT-TYPE
			SYNTAX SEQUENCE OF GOnuDerInfoEntry
			MAX-ACCESS not-accessible
			STATUS current
			DESCRIPTION
				"Description."
			::= { gOnuAuthList 23 }

		
--  1.3.6.1.4.1.37950.1.1.6.1.1.23.1
		-- 1.3.6.1.4.1.37950.1.1.6.1.1.23.1
		gOnuDerInfoEntry OBJECT-TYPE
			SYNTAX GOnuDerInfoEntry
			MAX-ACCESS not-accessible
			STATUS current
			DESCRIPTION
				"Description."
			INDEX { gOnuDerInfoPon, gOnuDerInfoOnu }
			::= { gOnuDerInfoTable 1 }

		
		GOnuDerInfoEntry ::=
			SEQUENCE { 
				gOnuDerInfoPon
					Integer32,
				gOnuDerInfoOnu
					Integer32,
				gOnuDerTime1
					OCTET STRING,
				gOnuDerReason1
					OCTET STRING,
				gOnuDerTime2
					OCTET STRING,
				gOnuDerReason2
					OCTET STRING,
				gOnuDerTime3
					OCTET STRING,
				gOnuDerReason3
					OCTET STRING,
				gOnuDerTime4
					OCTET STRING,
				gOnuDerReason4
					OCTET STRING,
				gOnuDerTime5
					OCTET STRING,
				gOnuDerReason5
					OCTET STRING
			 }

--  1.3.6.1.4.1.37950.1.1.6.1.1.23.1.1
		-- 1.3.6.1.4.1.37950.1.1.6.1.1.23.1.1
		gOnuDerInfoPon OBJECT-TYPE
			SYNTAX Integer32
			MAX-ACCESS read-only
			STATUS current
			DESCRIPTION
				"Description."
			::= { gOnuDerInfoEntry 1 }

		
--  1.3.6.1.4.1.37950.1.1.6.1.1.23.1.2
		-- 1.3.6.1.4.1.37950.1.1.6.1.1.23.1.2
		gOnuDerInfoOnu OBJECT-TYPE
			SYNTAX Integer32
			MAX-ACCESS read-only
			STATUS current
			DESCRIPTION
				"Description."
			::= { gOnuDerInfoEntry 2 }

		
--  1.3.6.1.4.1.37950.1.1.6.1.1.23.1.3
		-- 1.3.6.1.4.1.37950.1.1.6.1.1.23.1.3
		gOnuDerTime1 OBJECT-TYPE
			SYNTAX OCTET STRING
			MAX-ACCESS read-only
			STATUS current
			DESCRIPTION
				"Description."
			::= { gOnuDerInfoEntry 3 }

		
--  1.3.6.1.4.1.37950.1.1.6.1.1.23.1.4
		-- 1.3.6.1.4.1.37950.1.1.6.1.1.23.1.4
		gOnuDerReason1 OBJECT-TYPE
			SYNTAX OCTET STRING
			MAX-ACCESS read-only
			STATUS current
			DESCRIPTION
				"Description."
			::= { gOnuDerInfoEntry 4 }

		
--  1.3.6.1.4.1.37950.1.1.6.1.1.23.1.5
		-- 1.3.6.1.4.1.37950.1.1.6.1.1.23.1.5
		gOnuDerTime2 OBJECT-TYPE
			SYNTAX OCTET STRING
			MAX-ACCESS read-only
			STATUS current
			DESCRIPTION
				"Description."
			::= { gOnuDerInfoEntry 5 }

		
--  1.3.6.1.4.1.37950.1.1.6.1.1.23.1.6
		-- 1.3.6.1.4.1.37950.1.1.6.1.1.23.1.6
		gOnuDerReason2 OBJECT-TYPE
			SYNTAX OCTET STRING
			MAX-ACCESS read-only
			STATUS current
			DESCRIPTION
				"Description."
			::= { gOnuDerInfoEntry 6 }

		
--  1.3.6.1.4.1.37950.1.1.6.1.1.23.1.7
		-- 1.3.6.1.4.1.37950.1.1.6.1.1.23.1.7
		gOnuDerTime3 OBJECT-TYPE
			SYNTAX OCTET STRING
			MAX-ACCESS read-only
			STATUS current
			DESCRIPTION
				"Description."
			::= { gOnuDerInfoEntry 7 }

		
--  1.3.6.1.4.1.37950.1.1.6.1.1.23.1.8
		-- 1.3.6.1.4.1.37950.1.1.6.1.1.23.1.8
		gOnuDerReason3 OBJECT-TYPE
			SYNTAX OCTET STRING
			MAX-ACCESS read-only
			STATUS current
			DESCRIPTION
				"Description."
			::= { gOnuDerInfoEntry 8 }

		
--  1.3.6.1.4.1.37950.1.1.6.1.1.23.1.9
		-- 1.3.6.1.4.1.37950.1.1.6.1.1.23.1.9
		gOnuDerTime4 OBJECT-TYPE
			SYNTAX OCTET STRING
			MAX-ACCESS read-only
			STATUS current
			DESCRIPTION
				"Description."
			::= { gOnuDerInfoEntry 9 }

		
--  1.3.6.1.4.1.37950.1.1.6.1.1.23.1.10
		-- 1.3.6.1.4.1.37950.1.1.6.1.1.23.1.10
		gOnuDerReason4 OBJECT-TYPE
			SYNTAX OCTET STRING
			MAX-ACCESS read-only
			STATUS current
			DESCRIPTION
				"Description."
			::= { gOnuDerInfoEntry 10 }

		
--  1.3.6.1.4.1.37950.1.1.6.1.1.23.1.11
		-- 1.3.6.1.4.1.37950.1.1.6.1.1.23.1.11
		gOnuDerTime5 OBJECT-TYPE
			SYNTAX OCTET STRING
			MAX-ACCESS read-only
			STATUS current
			DESCRIPTION
				"Description."
			::= { gOnuDerInfoEntry 11 }

		
--  1.3.6.1.4.1.37950.1.1.6.1.1.23.1.12
		-- 1.3.6.1.4.1.37950.1.1.6.1.1.23.1.12
		gOnuDerReason5 OBJECT-TYPE
			SYNTAX OCTET STRING
			MAX-ACCESS read-only
			STATUS current
			DESCRIPTION
				"Description."
			::= { gOnuDerInfoEntry 12 }

		
--  1.3.6.1.4.1.37950.1.1.6.1.2
		-- 1.3.6.1.4.1.37950.1.1.6.1.2
		gOnuAutoFind OBJECT IDENTIFIER ::= { v1600gOnu 2 }

		
--  1.3.6.1.4.1.37950.1.1.6.1.2.1
		-- 1.3.6.1.4.1.37950.1.1.6.1.2.1
		gOnuAutoFindBaseTable OBJECT-TYPE
			SYNTAX SEQUENCE OF GOnuAutoFindBaseEntry
			MAX-ACCESS not-accessible
			STATUS current
			DESCRIPTION
				"Description."
			::= { gOnuAutoFind 1 }

		
--  1.3.6.1.4.1.37950.1.1.6.1.2.1.1
		-- 1.3.6.1.4.1.37950.1.1.6.1.2.1.1
		gOnuAutoFindBaseEntry OBJECT-TYPE
			SYNTAX GOnuAutoFindBaseEntry
			MAX-ACCESS not-accessible
			STATUS current
			DESCRIPTION
				"Description."
			INDEX { gOnuAutoFindBasePonInx, gOnuAutoFindBaseOnuInx }
			::= { gOnuAutoFindBaseTable 1 }

		
		GOnuAutoFindBaseEntry ::=
			SEQUENCE { 
				gOnuAutoFindBasePonInx
					INTEGER,
				gOnuAutoFindBaseOnuInx
					INTEGER,
				gOnuAutoFindBaseSn
					OCTET STRING,
				gOnuAutoFindBaseState
					INTEGER
			 }

--  1.3.6.1.4.1.37950.1.1.6.1.2.1.1.1
		-- 1.3.6.1.4.1.37950.1.1.6.1.2.1.1.1
		gOnuAutoFindBasePonInx OBJECT-TYPE
			SYNTAX INTEGER (1..16)
			MAX-ACCESS read-write
			STATUS current
			DESCRIPTION
				"Description."
			::= { gOnuAutoFindBaseEntry 1 }

		
--  1.3.6.1.4.1.37950.1.1.6.1.2.1.1.2
		-- 1.3.6.1.4.1.37950.1.1.6.1.2.1.1.2
		gOnuAutoFindBaseOnuInx OBJECT-TYPE
			SYNTAX INTEGER (1..128)
			MAX-ACCESS read-write
			STATUS current
			DESCRIPTION
				"Description."
			::= { gOnuAutoFindBaseEntry 2 }

		
--  1.3.6.1.4.1.37950.1.1.6.1.2.1.1.3
		-- 1.3.6.1.4.1.37950.1.1.6.1.2.1.1.3
		gOnuAutoFindBaseSn OBJECT-TYPE
			SYNTAX OCTET STRING
			MAX-ACCESS read-only
			STATUS current
			DESCRIPTION
				"Description."
			::= { gOnuAutoFindBaseEntry 3 }

		
--  1.3.6.1.4.1.37950.1.1.6.1.2.1.1.4
		-- 1.3.6.1.4.1.37950.1.1.6.1.2.1.1.4
		gOnuAutoFindBaseState OBJECT-TYPE
			SYNTAX INTEGER (0..7)
			MAX-ACCESS read-only
			STATUS current
			DESCRIPTION
				"Description."
			::= { gOnuAutoFindBaseEntry 4 }

		
--  1.3.6.1.4.1.37950.1.1.6.1.2.2
		-- 1.3.6.1.4.1.37950.1.1.6.1.2.2
		gOnuAutoFindDetailTable OBJECT-TYPE
			SYNTAX SEQUENCE OF GOnuAutoFindDetailEntry
			MAX-ACCESS not-accessible
			STATUS current
			DESCRIPTION
				"Description."
			::= { gOnuAutoFind 2 }

		
--  1.3.6.1.4.1.37950.1.1.6.1.2.2.1
		-- 1.3.6.1.4.1.37950.1.1.6.1.2.2.1
		gOnuAutoFindDetailEntry OBJECT-TYPE
			SYNTAX GOnuAutoFindDetailEntry
			MAX-ACCESS not-accessible
			STATUS current
			DESCRIPTION
				"Description."
			INDEX { gOnuAutoFindDetailPonInx, gOnuAutoFindDetailOnuInx }
			::= { gOnuAutoFindDetailTable 1 }

		
		GOnuAutoFindDetailEntry ::=
			SEQUENCE { 
				gOnuAutoFindDetailPonInx
					INTEGER,
				gOnuAutoFindDetailOnuInx
					INTEGER,
				gOnuAutoFindDetailSn
					OCTET STRING,
				gOnuAutoFindDetailPw
					OCTET STRING,
				gOnuAutoFindDetailLoid
					OCTET STRING,
				gOnuAutoFindDetailLoidPw
					OCTET STRING,
				gOnuAutoFindDetailModel
					OCTET STRING,
				gOnuAutoFindDetailVersion
					OCTET STRING
			 }

--  1.3.6.1.4.1.37950.1.1.6.1.2.2.1.1
		-- 1.3.6.1.4.1.37950.1.1.6.1.2.2.1.1
		gOnuAutoFindDetailPonInx OBJECT-TYPE
			SYNTAX INTEGER (1..16)
			MAX-ACCESS read-only
			STATUS current
			DESCRIPTION
				"Description."
			::= { gOnuAutoFindDetailEntry 1 }

		
--  1.3.6.1.4.1.37950.1.1.6.1.2.2.1.2
		-- 1.3.6.1.4.1.37950.1.1.6.1.2.2.1.2
		gOnuAutoFindDetailOnuInx OBJECT-TYPE
			SYNTAX INTEGER (1..128)
			MAX-ACCESS read-only
			STATUS current
			DESCRIPTION
				"Description."
			::= { gOnuAutoFindDetailEntry 2 }

		
--  1.3.6.1.4.1.37950.1.1.6.1.2.2.1.3
		-- 1.3.6.1.4.1.37950.1.1.6.1.2.2.1.3
		gOnuAutoFindDetailSn OBJECT-TYPE
			SYNTAX OCTET STRING
			MAX-ACCESS read-only
			STATUS current
			DESCRIPTION
				"Description."
			::= { gOnuAutoFindDetailEntry 3 }

		
--  1.3.6.1.4.1.37950.1.1.6.1.2.2.1.4
		-- 1.3.6.1.4.1.37950.1.1.6.1.2.2.1.4
		gOnuAutoFindDetailPw OBJECT-TYPE
			SYNTAX OCTET STRING
			MAX-ACCESS read-only
			STATUS current
			DESCRIPTION
				"Description."
			::= { gOnuAutoFindDetailEntry 4 }

		
--  1.3.6.1.4.1.37950.1.1.6.1.2.2.1.5
		-- 1.3.6.1.4.1.37950.1.1.6.1.2.2.1.5
		gOnuAutoFindDetailLoid OBJECT-TYPE
			SYNTAX OCTET STRING
			MAX-ACCESS read-only
			STATUS current
			DESCRIPTION
				"Description."
			::= { gOnuAutoFindDetailEntry 5 }

		
--  1.3.6.1.4.1.37950.1.1.6.1.2.2.1.6
		-- 1.3.6.1.4.1.37950.1.1.6.1.2.2.1.6
		gOnuAutoFindDetailLoidPw OBJECT-TYPE
			SYNTAX OCTET STRING
			MAX-ACCESS read-write
			STATUS current
			DESCRIPTION
				"Description."
			::= { gOnuAutoFindDetailEntry 6 }

		
--  1.3.6.1.4.1.37950.1.1.6.1.2.2.1.7
		-- 1.3.6.1.4.1.37950.1.1.6.1.2.2.1.7
		gOnuAutoFindDetailModel OBJECT-TYPE
			SYNTAX OCTET STRING
			MAX-ACCESS read-write
			STATUS current
			DESCRIPTION
				"Description."
			::= { gOnuAutoFindDetailEntry 7 }

		
--  1.3.6.1.4.1.37950.1.1.6.1.2.2.1.8
		-- 1.3.6.1.4.1.37950.1.1.6.1.2.2.1.8
		gOnuAutoFindDetailVersion OBJECT-TYPE
			SYNTAX OCTET STRING
			MAX-ACCESS read-only
			STATUS current
			DESCRIPTION
				"Description."
			::= { gOnuAutoFindDetailEntry 8 }

		
--  1.3.6.1.4.1.37950.1.1.6.1.2.3
		-- 1.3.6.1.4.1.37950.1.1.6.1.2.3
		gOnuAutoFindOnuConfirm OBJECT IDENTIFIER ::= { gOnuAutoFind 3 }

		
--  1.3.6.1.4.1.37950.1.1.6.1.2.3.1
		-- 1.3.6.1.4.1.37950.1.1.6.1.2.3.1
		gOnuAutoFindOnuConfirmPonId OBJECT-TYPE
			SYNTAX Integer32 (1..16)
			MAX-ACCESS read-write
			STATUS current
			DESCRIPTION
				"Description."
			::= { gOnuAutoFindOnuConfirm 1 }

		
--  1.3.6.1.4.1.37950.1.1.6.1.2.3.2
		-- 1.3.6.1.4.1.37950.1.1.6.1.2.3.2
		gOnuAutoFindOnuConfirmAuthMode OBJECT-TYPE
			SYNTAX INTEGER
				{
				sn(1),
				loid(6)
				}
			MAX-ACCESS read-write
			STATUS current
			DESCRIPTION
				"Description."
			::= { gOnuAutoFindOnuConfirm 2 }

		
--  1.3.6.1.4.1.37950.1.1.6.1.2.3.3
		-- 1.3.6.1.4.1.37950.1.1.6.1.2.3.3
		gOnuAutoFindOnuConfirmOnuProfile OBJECT-TYPE
			SYNTAX OCTET STRING
			MAX-ACCESS read-write
			STATUS current
			DESCRIPTION
				"Description."
			::= { gOnuAutoFindOnuConfirm 3 }

		
--  1.3.6.1.4.1.37950.1.1.6.1.2.3.4
		-- 1.3.6.1.4.1.37950.1.1.6.1.2.3.4
		gOnuAutoFindOnuConfirmLineProfile OBJECT-TYPE
			SYNTAX OCTET STRING
			MAX-ACCESS read-write
			STATUS current
			DESCRIPTION
				"Description."
			::= { gOnuAutoFindOnuConfirm 4 }

		
--  1.3.6.1.4.1.37950.1.1.6.1.2.3.5
		-- 1.3.6.1.4.1.37950.1.1.6.1.2.3.5
		gOnuAutoFindOnuConfirmSrvProfile OBJECT-TYPE
			SYNTAX OCTET STRING
			MAX-ACCESS read-write
			STATUS current
			DESCRIPTION
				"Description."
			::= { gOnuAutoFindOnuConfirm 5 }

		
--  1.3.6.1.4.1.37950.1.1.6.1.2.3.6
		-- 1.3.6.1.4.1.37950.1.1.6.1.2.3.6
		gOnuAutoFindOnuConfirmAlarmProfile OBJECT-TYPE
			SYNTAX OCTET STRING
			MAX-ACCESS read-write
			STATUS current
			DESCRIPTION
				"Description."
			::= { gOnuAutoFindOnuConfirm 6 }

		
--  1.3.6.1.4.1.37950.1.1.6.1.2.3.7
		-- 1.3.6.1.4.1.37950.1.1.6.1.2.3.7
		gOnuAutoFindOnuConfirmPriProfile OBJECT-TYPE
			SYNTAX OCTET STRING
			MAX-ACCESS read-write
			STATUS current
			DESCRIPTION
				"Description."
			::= { gOnuAutoFindOnuConfirm 7 }

		
--  1.3.6.1.4.1.37950.1.1.6.1.2.3.8
		-- 1.3.6.1.4.1.37950.1.1.6.1.2.3.8
		gOnuAutoFindOnuConfirmAction OBJECT-TYPE
			SYNTAX INTEGER { commit(1) }
			MAX-ACCESS read-write
			STATUS current
			DESCRIPTION
				"Description."
			::= { gOnuAutoFindOnuConfirm 8 }

		
--  1.3.6.1.4.1.37950.1.1.6.1.2.3.9
		-- 1.3.6.1.4.1.37950.1.1.6.1.2.3.9
		gOnuAutoFindOnuConfirmFmtProfile OBJECT-TYPE
			SYNTAX OCTET STRING
			MAX-ACCESS read-write
			STATUS current
			DESCRIPTION
				"Description."
			::= { gOnuAutoFindOnuConfirm 9 }

		
--  1.3.6.1.4.1.37950.1.1.6.1.3
		-- 1.3.6.1.4.1.37950.1.1.6.1.3
		gOnuAutoLearn OBJECT IDENTIFIER ::= { v1600gOnu 3 }

		
--  1.3.6.1.4.1.37950.1.1.6.1.3.1
		-- 1.3.6.1.4.1.37950.1.1.6.1.3.1
		gOnuAutoLearnTable OBJECT-TYPE
			SYNTAX SEQUENCE OF GOnuAutoLearnEntry
			MAX-ACCESS not-accessible
			STATUS current
			DESCRIPTION
				"Description."
			::= { gOnuAutoLearn 1 }

		
--  1.3.6.1.4.1.37950.1.1.6.1.3.1.1
		-- 1.3.6.1.4.1.37950.1.1.6.1.3.1.1
		gOnuAutoLearnEntry OBJECT-TYPE
			SYNTAX GOnuAutoLearnEntry
			MAX-ACCESS not-accessible
			STATUS current
			DESCRIPTION
				"Description."
			INDEX { gOnuAutoLearnPonInx }
			::= { gOnuAutoLearnTable 1 }

		
		GOnuAutoLearnEntry ::=
			SEQUENCE { 
				gOnuAutoLearnPonInx
					Integer32,
				gOnuAutoLearnSta
					INTEGER,
				gOnuAutoLearnDefaultProfile
					OCTET STRING,
				gOnuAutoLearnLineProfile
					OCTET STRING,
				gOnuAutoLearnSrvProfile
					OCTET STRING,
				gOnuAutoLearnAlarmProfile
					OCTET STRING,
				gOnuAutoLearnPriProfile
					OCTET STRING,
				gOnuAutoLearnDefPlugAndPlay
					INTEGER,
				gOnuAutoLearnPlugAndPlay
					INTEGER,
				gOnuAutoLearnFormatProfile
					OCTET STRING,
				gOnuAutoLearnDefaultVlan
					Integer32
			 }

--  1.3.6.1.4.1.37950.1.1.6.1.3.1.1.1
		-- 1.3.6.1.4.1.37950.1.1.6.1.3.1.1.1
		gOnuAutoLearnPonInx OBJECT-TYPE
			SYNTAX Integer32 (1..16)
			MAX-ACCESS read-only
			STATUS current
			DESCRIPTION
				"Description."
			::= { gOnuAutoLearnEntry 1 }

		
--  1.3.6.1.4.1.37950.1.1.6.1.3.1.1.2
		-- 1.3.6.1.4.1.37950.1.1.6.1.3.1.1.2
		gOnuAutoLearnSta OBJECT-TYPE
			SYNTAX INTEGER
				{
				disable(0),
				enable(1)
				}
			MAX-ACCESS read-write
			STATUS current
			DESCRIPTION
				"Description."
			::= { gOnuAutoLearnEntry 2 }

		
--  1.3.6.1.4.1.37950.1.1.6.1.3.1.1.3
		-- 1.3.6.1.4.1.37950.1.1.6.1.3.1.1.3
		gOnuAutoLearnDefaultProfile OBJECT-TYPE
			SYNTAX OCTET STRING
			MAX-ACCESS read-write
			STATUS current
			DESCRIPTION
				"Description."
			DEFVAL { "default" }
			::= { gOnuAutoLearnEntry 3 }

		
--  1.3.6.1.4.1.37950.1.1.6.1.3.1.1.4
		-- 1.3.6.1.4.1.37950.1.1.6.1.3.1.1.4
		gOnuAutoLearnLineProfile OBJECT-TYPE
			SYNTAX OCTET STRING
			MAX-ACCESS read-write
			STATUS current
			DESCRIPTION
				"Description."
			::= { gOnuAutoLearnEntry 4 }

		
--  1.3.6.1.4.1.37950.1.1.6.1.3.1.1.5
		-- 1.3.6.1.4.1.37950.1.1.6.1.3.1.1.5
		gOnuAutoLearnSrvProfile OBJECT-TYPE
			SYNTAX OCTET STRING
			MAX-ACCESS read-write
			STATUS current
			DESCRIPTION
				"Description."
			::= { gOnuAutoLearnEntry 5 }

		
--  1.3.6.1.4.1.37950.1.1.6.1.3.1.1.6
		-- 1.3.6.1.4.1.37950.1.1.6.1.3.1.1.6
		gOnuAutoLearnAlarmProfile OBJECT-TYPE
			SYNTAX OCTET STRING
			MAX-ACCESS read-write
			STATUS current
			DESCRIPTION
				"Description."
			::= { gOnuAutoLearnEntry 6 }

		
--  1.3.6.1.4.1.37950.1.1.6.1.3.1.1.7
		-- 1.3.6.1.4.1.37950.1.1.6.1.3.1.1.7
		gOnuAutoLearnPriProfile OBJECT-TYPE
			SYNTAX OCTET STRING
			MAX-ACCESS read-write
			STATUS current
			DESCRIPTION
				"Description."
			::= { gOnuAutoLearnEntry 7 }

		
--  1.3.6.1.4.1.37950.1.1.6.1.3.1.1.8
		-- 1.3.6.1.4.1.37950.1.1.6.1.3.1.1.8
		gOnuAutoLearnDefPlugAndPlay OBJECT-TYPE
			SYNTAX INTEGER
				{
				disable(0),
				enable(1)
				}
			MAX-ACCESS read-write
			STATUS current
			DESCRIPTION
				"Description."
			::= { gOnuAutoLearnEntry 8 }

		
--  1.3.6.1.4.1.37950.1.1.6.1.3.1.1.9
		-- 1.3.6.1.4.1.37950.1.1.6.1.3.1.1.9
		gOnuAutoLearnPlugAndPlay OBJECT-TYPE
			SYNTAX INTEGER
				{
				disable(0),
				enable(1)
				}
			MAX-ACCESS read-write
			STATUS current
			DESCRIPTION
				"Description."
			::= { gOnuAutoLearnEntry 9 }

		
--  1.3.6.1.4.1.37950.1.1.6.1.3.1.1.10
		-- 1.3.6.1.4.1.37950.1.1.6.1.3.1.1.10
		gOnuAutoLearnFormatProfile OBJECT-TYPE
			SYNTAX OCTET STRING
			MAX-ACCESS read-write
			STATUS current
			DESCRIPTION
				"Description."
			::= { gOnuAutoLearnEntry 10 }

		
--  1.3.6.1.4.1.37950.1.1.6.1.3.1.1.11
		-- 1.3.6.1.4.1.37950.1.1.6.1.3.1.1.11
		gOnuAutoLearnDefaultVlan OBJECT-TYPE
			SYNTAX Integer32 (1..4094)
			MAX-ACCESS read-write
			STATUS current
			DESCRIPTION
				"Description."
			::= { gOnuAutoLearnEntry 11 }

		
--  1.3.6.1.4.1.37950.1.1.6.1.3.2
		-- 1.3.6.1.4.1.37950.1.1.6.1.3.2
		gOnuAutoBind OBJECT IDENTIFIER ::= { gOnuAutoLearn 2 }

		
--  1.3.6.1.4.1.37950.1.1.6.1.3.2.1
		-- 1.3.6.1.4.1.37950.1.1.6.1.3.2.1
		gOnuAutoBindEquId OBJECT-TYPE
			SYNTAX OCTET STRING
			MAX-ACCESS read-write
			STATUS current
			DESCRIPTION
				"Description."
			::= { gOnuAutoBind 1 }

		
--  1.3.6.1.4.1.37950.1.1.6.1.3.2.2
		-- 1.3.6.1.4.1.37950.1.1.6.1.3.2.2
		gOnuAutoBindOnuProfile OBJECT-TYPE
			SYNTAX OCTET STRING
			MAX-ACCESS read-write
			STATUS current
			DESCRIPTION
				"Description."
			::= { gOnuAutoBind 2 }

		
--  1.3.6.1.4.1.37950.1.1.6.1.3.2.3
		-- 1.3.6.1.4.1.37950.1.1.6.1.3.2.3
		gOnuAutoBindLineProfile OBJECT-TYPE
			SYNTAX OCTET STRING
			MAX-ACCESS read-write
			STATUS current
			DESCRIPTION
				"Description."
			::= { gOnuAutoBind 3 }

		
--  1.3.6.1.4.1.37950.1.1.6.1.3.2.4
		-- 1.3.6.1.4.1.37950.1.1.6.1.3.2.4
		gOnuAutoBindSrvProfile OBJECT-TYPE
			SYNTAX OCTET STRING
			MAX-ACCESS read-write
			STATUS current
			DESCRIPTION
				"Description."
			::= { gOnuAutoBind 4 }

		
--  1.3.6.1.4.1.37950.1.1.6.1.3.2.5
		-- 1.3.6.1.4.1.37950.1.1.6.1.3.2.5
		gOnuAutoBindAlarmProfile OBJECT-TYPE
			SYNTAX OCTET STRING
			MAX-ACCESS read-write
			STATUS current
			DESCRIPTION
				"Description."
			::= { gOnuAutoBind 5 }

		
--  1.3.6.1.4.1.37950.1.1.6.1.3.2.6
		-- 1.3.6.1.4.1.37950.1.1.6.1.3.2.6
		gOnuAutoBindAction OBJECT-TYPE
			SYNTAX INTEGER
				{
				add(1),
				del(2)
				}
			MAX-ACCESS read-write
			STATUS current
			DESCRIPTION
				"Description."
			::= { gOnuAutoBind 6 }

		
--  1.3.6.1.4.1.37950.1.1.6.1.3.2.7
		-- 1.3.6.1.4.1.37950.1.1.6.1.3.2.7
		gOnuAutoBindPriProfile OBJECT-TYPE
			SYNTAX OCTET STRING
			MAX-ACCESS read-write
			STATUS current
			DESCRIPTION
				"Description."
			::= { gOnuAutoBind 7 }

		
--  1.3.6.1.4.1.37950.1.1.6.1.3.2.8
		-- 1.3.6.1.4.1.37950.1.1.6.1.3.2.8
		gOnuAutoBindFormatProfile OBJECT-TYPE
			SYNTAX OCTET STRING
			MAX-ACCESS read-write
			STATUS current
			DESCRIPTION
				"Description."
			::= { gOnuAutoBind 8 }

		
--  1.3.6.1.4.1.37950.1.1.6.1.3.3
		-- 1.3.6.1.4.1.37950.1.1.6.1.3.3
		gOnuAutoBindTable OBJECT-TYPE
			SYNTAX SEQUENCE OF GOnuAutoBindEntry
			MAX-ACCESS not-accessible
			STATUS current
			DESCRIPTION
				"Description."
			::= { gOnuAutoLearn 3 }

		
--  1.3.6.1.4.1.37950.1.1.6.1.3.3.1
		-- 1.3.6.1.4.1.37950.1.1.6.1.3.3.1
		gOnuAutoBindEntry OBJECT-TYPE
			SYNTAX GOnuAutoBindEntry
			MAX-ACCESS not-accessible
			STATUS current
			DESCRIPTION
				"Description."
			INDEX { gOnuAutoBindTEquId }
			::= { gOnuAutoBindTable 1 }

		
		GOnuAutoBindEntry ::=
			SEQUENCE { 
				gOnuAutoBindTEquId
					OCTET STRING,
				gOnuAutoBindTOnuProfile
					OCTET STRING,
				gOnuAutoBindTLineProfile
					OCTET STRING,
				gOnuAutoBindTSrvProfile
					OCTET STRING,
				gOnuAutoBindTAlarmProfile
					OCTET STRING,
				gOnuAutoBindTPriProfile
					OCTET STRING,
				gOnuAutoBindTFormatProfile
					OCTET STRING
			 }

--  1.3.6.1.4.1.37950.1.1.6.1.3.3.1.1
		-- 1.3.6.1.4.1.37950.1.1.6.1.3.3.1.1
		gOnuAutoBindTEquId OBJECT-TYPE
			SYNTAX OCTET STRING
			MAX-ACCESS read-only
			STATUS current
			DESCRIPTION
				"Description."
			::= { gOnuAutoBindEntry 1 }

		
--  1.3.6.1.4.1.37950.1.1.6.1.3.3.1.2
		-- 1.3.6.1.4.1.37950.1.1.6.1.3.3.1.2
		gOnuAutoBindTOnuProfile OBJECT-TYPE
			SYNTAX OCTET STRING
			MAX-ACCESS read-write
			STATUS current
			DESCRIPTION
				"Description."
			::= { gOnuAutoBindEntry 2 }

		
--  1.3.6.1.4.1.37950.1.1.6.1.3.3.1.3
		-- 1.3.6.1.4.1.37950.1.1.6.1.3.3.1.3
		gOnuAutoBindTLineProfile OBJECT-TYPE
			SYNTAX OCTET STRING
			MAX-ACCESS read-write
			STATUS current
			DESCRIPTION
				"Description."
			::= { gOnuAutoBindEntry 3 }

		
--  1.3.6.1.4.1.37950.1.1.6.1.3.3.1.4
		-- 1.3.6.1.4.1.37950.1.1.6.1.3.3.1.4
		gOnuAutoBindTSrvProfile OBJECT-TYPE
			SYNTAX OCTET STRING
			MAX-ACCESS read-write
			STATUS current
			DESCRIPTION
				"Description."
			::= { gOnuAutoBindEntry 4 }

		
--  1.3.6.1.4.1.37950.1.1.6.1.3.3.1.5
		-- 1.3.6.1.4.1.37950.1.1.6.1.3.3.1.5
		gOnuAutoBindTAlarmProfile OBJECT-TYPE
			SYNTAX OCTET STRING
			MAX-ACCESS read-write
			STATUS current
			DESCRIPTION
				"Description."
			::= { gOnuAutoBindEntry 5 }

		
--  1.3.6.1.4.1.37950.1.1.6.1.3.3.1.6
		-- 1.3.6.1.4.1.37950.1.1.6.1.3.3.1.6
		gOnuAutoBindTPriProfile OBJECT-TYPE
			SYNTAX OCTET STRING
			MAX-ACCESS read-only
			STATUS current
			DESCRIPTION
				"Description."
			::= { gOnuAutoBindEntry 6 }

		
--  1.3.6.1.4.1.37950.1.1.6.1.3.3.1.7
		-- 1.3.6.1.4.1.37950.1.1.6.1.3.3.1.7
		gOnuAutoBindTFormatProfile OBJECT-TYPE
			SYNTAX OCTET STRING
			MAX-ACCESS read-write
			STATUS current
			DESCRIPTION
				"Description."
			::= { gOnuAutoBindEntry 7 }

		
--  1.3.6.1.4.1.37950.1.1.6.1.3.4
		-- 1.3.6.1.4.1.37950.1.1.6.1.3.4
		gOnuAutoBindMatchingType OBJECT IDENTIFIER ::= { gOnuAutoLearn 4 }

		
--  1.3.6.1.4.1.37950.1.1.6.1.3.4.1
		-- 1.3.6.1.4.1.37950.1.1.6.1.3.4.1
		gOnuAutoBindMatchingTypeAction OBJECT-TYPE
			SYNTAX INTEGER { commit(1) }
			MAX-ACCESS read-write
			STATUS current
			DESCRIPTION
				"Description."
			::= { gOnuAutoBindMatchingType 1 }

		
--  1.3.6.1.4.1.37950.1.1.6.1.3.4.2
		-- 1.3.6.1.4.1.37950.1.1.6.1.3.4.2
		gOnuAutoBindMatchingTypeSelect OBJECT-TYPE
			SYNTAX INTEGER
				{
				exact_matching(0),
				fuzzy_matching(1)
				}
			MAX-ACCESS read-write
			STATUS current
			DESCRIPTION
				"Description."
			::= { gOnuAutoBindMatchingType 2 }

		
--   1.3.6.1.4.1.37950.1.1.5.12.2.2
-- 1.3.6.1.4.1.37950.1.1.6.1.4
		-- 1.3.6.1.4.1.37950.1.1.6.1.4
		gOnuUpgrade OBJECT IDENTIFIER ::= { v1600gOnu 4 }

		
--   1.3.6.1.4.1.37950.1.1.5.12.2.2.1
-- 1.3.6.1.4.1.37950.1.1.6.1.4.1
		-- 1.3.6.1.4.1.37950.1.1.6.1.4.1
		gOnuUpTftpLoadFile OBJECT IDENTIFIER ::= { gOnuUpgrade 1 }

		
--   1.3.6.1.4.1.37950.1.1.5.12.2.2.1.1
-- 1.3.6.1.4.1.37950.1.1.6.1.4.1.1
		-- 1.3.6.1.4.1.37950.1.1.6.1.4.1.1
		gOnuUpTftpLoadFileName OBJECT-TYPE
			SYNTAX OCTET STRING
			MAX-ACCESS read-write
			STATUS current
			DESCRIPTION
				"Description."
			::= { gOnuUpTftpLoadFile 1 }

		
--   1.3.6.1.4.1.37950.1.1.5.12.2.2.1.2
-- 1.3.6.1.4.1.37950.1.1.6.1.4.1.2
		-- 1.3.6.1.4.1.37950.1.1.6.1.4.1.2
		gOnuUpTftpLoadFileServer OBJECT-TYPE
			SYNTAX OCTET STRING
			MAX-ACCESS read-write
			STATUS current
			DESCRIPTION
				"Description."
			::= { gOnuUpTftpLoadFile 2 }

		
--   1.3.6.1.4.1.37950.1.1.5.12.2.2.1.3
-- 1.3.6.1.4.1.37950.1.1.6.1.4.1.3
		-- 1.3.6.1.4.1.37950.1.1.6.1.4.1.3
		gOnuUpTftpLoadFileAction OBJECT-TYPE
			SYNTAX INTEGER { commit(1) }
			MAX-ACCESS read-write
			STATUS current
			DESCRIPTION
				"Description."
			::= { gOnuUpTftpLoadFile 3 }

		
--  1.3.6.1.4.1.37950.1.1.6.1.4.2
		-- 1.3.6.1.4.1.37950.1.1.6.1.4.2
		gOnuUpOnuImgTable OBJECT-TYPE
			SYNTAX SEQUENCE OF GOnuUpOnuImgEntry
			MAX-ACCESS not-accessible
			STATUS current
			DESCRIPTION
				"Description."
			::= { gOnuUpgrade 2 }

		
--  1.3.6.1.4.1.37950.1.1.6.1.4.2.1
		-- 1.3.6.1.4.1.37950.1.1.6.1.4.2.1
		gOnuUpOnuImgEntry OBJECT-TYPE
			SYNTAX GOnuUpOnuImgEntry
			MAX-ACCESS not-accessible
			STATUS current
			DESCRIPTION
				"Description."
			INDEX { gOnuUpOnuImg }
			::= { gOnuUpOnuImgTable 1 }

		
		GOnuUpOnuImgEntry ::=
			SEQUENCE { 
				gOnuUpOnuImg
					OCTET STRING
			 }

--  1.3.6.1.4.1.37950.1.1.6.1.4.2.1.1
		-- 1.3.6.1.4.1.37950.1.1.6.1.4.2.1.1
		gOnuUpOnuImg OBJECT-TYPE
			SYNTAX OCTET STRING
			MAX-ACCESS read-only
			STATUS current
			DESCRIPTION
				"Description."
			::= { gOnuUpOnuImgEntry 1 }

		
--   1.3.6.1.4.1.37950.1.1.5.12.2.2.3
-- 1.3.6.1.4.1.37950.1.1.6.1.4.3
		-- 1.3.6.1.4.1.37950.1.1.6.1.4.3
		gOnuUpManu OBJECT IDENTIFIER ::= { gOnuUpgrade 3 }

		
--   1.3.6.1.4.1.37950.1.1.5.12.2.2.3.1
-- 1.3.6.1.4.1.37950.1.1.6.1.4.3.1
		-- 1.3.6.1.4.1.37950.1.1.6.1.4.3.1
		gOnuUpManuImg OBJECT-TYPE
			SYNTAX OCTET STRING
			MAX-ACCESS read-write
			STATUS current
			DESCRIPTION
				"Description."
			::= { gOnuUpManu 1 }

		
--   1.3.6.1.4.1.37950.1.1.5.12.2.2.3.2
-- 1.3.6.1.4.1.37950.1.1.6.1.4.3.2
		-- 1.3.6.1.4.1.37950.1.1.6.1.4.3.2
		gOnuUpManuPonInx OBJECT-TYPE
			SYNTAX Integer32 (1..16)
			MAX-ACCESS read-write
			STATUS current
			DESCRIPTION
				"Description."
			::= { gOnuUpManu 2 }

		
--   1.3.6.1.4.1.37950.1.1.5.12.2.2.3.3
-- 1.3.6.1.4.1.37950.1.1.6.1.4.3.3
		-- 1.3.6.1.4.1.37950.1.1.6.1.4.3.3
		gOnuUpManuOnuList OBJECT-TYPE
			SYNTAX OCTET STRING
			MAX-ACCESS read-write
			STATUS current
			DESCRIPTION
				"Description."
			::= { gOnuUpManu 3 }

		
--   1.3.6.1.4.1.37950.1.1.5.12.2.2.3.3
-- 1.3.6.1.4.1.37950.1.1.6.1.4.3.4
		-- 1.3.6.1.4.1.37950.1.1.6.1.4.3.4
		gOnuUpManuMode OBJECT-TYPE
			SYNTAX INTEGER
				{
				download(1),
				active(2),
				commit(3),
				mix(4),
				quick_active(5)
				}
			MAX-ACCESS read-write
			STATUS current
			DESCRIPTION
				"Description."
			::= { gOnuUpManu 4 }

		
--   1.3.6.1.4.1.37950.1.1.5.12.2.2.3.3
-- 1.3.6.1.4.1.37950.1.1.6.1.4.3.5
		-- 1.3.6.1.4.1.37950.1.1.6.1.4.3.5
		gOnuUpManuAction OBJECT-TYPE
			SYNTAX INTEGER
				{
				start(1),
				stop(2)
				}
			MAX-ACCESS read-write
			STATUS current
			DESCRIPTION
				"Description."
			::= { gOnuUpManu 5 }

		
--  1.3.6.1.4.1.37950.1.1.6.1.4.3.6
		-- 1.3.6.1.4.1.37950.1.1.6.1.4.3.6
		gOnuUpManuImgdel OBJECT-TYPE
			SYNTAX INTEGER { del(0) }
			MAX-ACCESS read-write
			STATUS current
			DESCRIPTION
				"Description."
			::= { gOnuUpManu 6 }

		
--  1.3.6.1.4.1.37950.1.1.6.1.4.4
		-- 1.3.6.1.4.1.37950.1.1.6.1.4.4
		gOnuUpManuInfoTable OBJECT-TYPE
			SYNTAX SEQUENCE OF GOnuUpManuInfoEntry
			MAX-ACCESS not-accessible
			STATUS current
			DESCRIPTION
				"Description."
			::= { gOnuUpgrade 4 }

		
--  1.3.6.1.4.1.37950.1.1.6.1.4.4.1
		-- 1.3.6.1.4.1.37950.1.1.6.1.4.4.1
		gOnuUpManuInfoEntry OBJECT-TYPE
			SYNTAX GOnuUpManuInfoEntry
			MAX-ACCESS not-accessible
			STATUS current
			DESCRIPTION
				"Description."
			INDEX { gOnuUpManuInfoImg }
			::= { gOnuUpManuInfoTable 1 }

		
		GOnuUpManuInfoEntry ::=
			SEQUENCE { 
				gOnuUpManuInfoImg
					OCTET STRING,
				gOnuUpManuInfoPonInx
					Integer32,
				gOnuUpManuInfoOnuList
					OCTET STRING
			 }

--  1.3.6.1.4.1.37950.1.1.6.1.4.4.1.1
		-- 1.3.6.1.4.1.37950.1.1.6.1.4.4.1.1
		gOnuUpManuInfoImg OBJECT-TYPE
			SYNTAX OCTET STRING
			MAX-ACCESS read-only
			STATUS current
			DESCRIPTION
				"Description."
			::= { gOnuUpManuInfoEntry 1 }

		
--  1.3.6.1.4.1.37950.1.1.6.1.4.4.1.2
		-- 1.3.6.1.4.1.37950.1.1.6.1.4.4.1.2
		gOnuUpManuInfoPonInx OBJECT-TYPE
			SYNTAX Integer32 (1..16)
			MAX-ACCESS read-only
			STATUS current
			DESCRIPTION
				"Description."
			::= { gOnuUpManuInfoEntry 2 }

		
--  1.3.6.1.4.1.37950.1.1.6.1.4.4.1.3
		-- 1.3.6.1.4.1.37950.1.1.6.1.4.4.1.3
		gOnuUpManuInfoOnuList OBJECT-TYPE
			SYNTAX OCTET STRING
			MAX-ACCESS read-only
			STATUS current
			DESCRIPTION
				"Description."
			::= { gOnuUpManuInfoEntry 3 }

		
--  1.3.6.1.4.1.37950.1.1.6.1.4.5
		-- 1.3.6.1.4.1.37950.1.1.6.1.4.5
		gOnuUpAuto OBJECT IDENTIFIER ::= { gOnuUpgrade 5 }

		
--  1.3.6.1.4.1.37950.1.1.6.1.4.5.1
		-- 1.3.6.1.4.1.37950.1.1.6.1.4.5.1
		gOnuUpAutoEquId OBJECT-TYPE
			SYNTAX OCTET STRING
			MAX-ACCESS read-write
			STATUS current
			DESCRIPTION
				"Description."
			::= { gOnuUpAuto 1 }

		
--  1.3.6.1.4.1.37950.1.1.6.1.4.5.2
		-- 1.3.6.1.4.1.37950.1.1.6.1.4.5.2
		gOnuUpAutoSwVer OBJECT-TYPE
			SYNTAX OCTET STRING
			MAX-ACCESS read-write
			STATUS current
			DESCRIPTION
				"Description."
			::= { gOnuUpAuto 2 }

		
--  1.3.6.1.4.1.37950.1.1.6.1.4.5.3
		-- 1.3.6.1.4.1.37950.1.1.6.1.4.5.3
		gOnuUpAutoOnuImg OBJECT-TYPE
			SYNTAX OCTET STRING
			MAX-ACCESS read-write
			STATUS current
			DESCRIPTION
				"Description."
			::= { gOnuUpAuto 3 }

		
--  1.3.6.1.4.1.37950.1.1.6.1.4.5.4
		-- 1.3.6.1.4.1.37950.1.1.6.1.4.5.4
		gOnuUpAutoAction OBJECT-TYPE
			SYNTAX INTEGER
				{
				add(1),
				del(2)
				}
			MAX-ACCESS read-write
			STATUS current
			DESCRIPTION
				"Description."
			::= { gOnuUpAuto 4 }

		
--  1.3.6.1.4.1.37950.1.1.6.1.4.6
		-- 1.3.6.1.4.1.37950.1.1.6.1.4.6
		gOnuUpAutoInfoTable OBJECT-TYPE
			SYNTAX SEQUENCE OF GOnuUpAutoInfoEntry
			MAX-ACCESS not-accessible
			STATUS current
			DESCRIPTION
				"Description."
			::= { gOnuUpgrade 6 }

		
--  1.3.6.1.4.1.37950.1.1.6.1.4.6.1
		-- 1.3.6.1.4.1.37950.1.1.6.1.4.6.1
		gOnuUpAutoInfoEntry OBJECT-TYPE
			SYNTAX GOnuUpAutoInfoEntry
			MAX-ACCESS not-accessible
			STATUS current
			DESCRIPTION
				"Description."
			INDEX { gOnuUpAutoInfoEquId }
			::= { gOnuUpAutoInfoTable 1 }

		
		GOnuUpAutoInfoEntry ::=
			SEQUENCE { 
				gOnuUpAutoInfoEquId
					OCTET STRING,
				gOnuUpAutoInfoSwVer
					OCTET STRING,
				gOnuUpAutoInfoOnuImg
					OCTET STRING
			 }

--  1.3.6.1.4.1.37950.1.1.6.1.4.6.1.1
		-- 1.3.6.1.4.1.37950.1.1.6.1.4.6.1.1
		gOnuUpAutoInfoEquId OBJECT-TYPE
			SYNTAX OCTET STRING
			MAX-ACCESS read-only
			STATUS current
			DESCRIPTION
				"Description."
			::= { gOnuUpAutoInfoEntry 1 }

		
--  1.3.6.1.4.1.37950.1.1.6.1.4.6.1.2
		-- 1.3.6.1.4.1.37950.1.1.6.1.4.6.1.2
		gOnuUpAutoInfoSwVer OBJECT-TYPE
			SYNTAX OCTET STRING
			MAX-ACCESS read-only
			STATUS current
			DESCRIPTION
				"Description."
			::= { gOnuUpAutoInfoEntry 2 }

		
--  1.3.6.1.4.1.37950.1.1.6.1.4.6.1.3
		-- 1.3.6.1.4.1.37950.1.1.6.1.4.6.1.3
		gOnuUpAutoInfoOnuImg OBJECT-TYPE
			SYNTAX OCTET STRING
			MAX-ACCESS read-only
			STATUS current
			DESCRIPTION
				"Description."
			::= { gOnuUpAutoInfoEntry 3 }

		
--  1.3.6.1.4.1.37950.1.1.6.1.4.7
		-- 1.3.6.1.4.1.37950.1.1.6.1.4.7
		gOnuUpStatusTable OBJECT-TYPE
			SYNTAX SEQUENCE OF GOnuUpStatusEntry
			MAX-ACCESS not-accessible
			STATUS current
			DESCRIPTION
				"Description."
			::= { gOnuUpgrade 7 }

		
--  1.3.6.1.4.1.37950.1.1.6.1.4.7.1
		-- 1.3.6.1.4.1.37950.1.1.6.1.4.7.1
		gOnuUpStatusEntry OBJECT-TYPE
			SYNTAX GOnuUpStatusEntry
			MAX-ACCESS not-accessible
			STATUS current
			DESCRIPTION
				"Description."
			INDEX { gOnuUpStatusPonInx, gOnuUpStatusOnuInx }
			::= { gOnuUpStatusTable 1 }

		
		GOnuUpStatusEntry ::=
			SEQUENCE { 
				gOnuUpStatusPonInx
					Integer32,
				gOnuUpStatusOnuInx
					Integer32,
				gOnuUpStatusAction
					INTEGER,
				gOnuUpStatusSta
					OCTET STRING,
				gOnuUpStatusProgress
					OCTET STRING,
				gOnuUpStatusFailreason
					OCTET STRING,
				gOnuUpStatusCommitTime
					OCTET STRING
			 }

--  1.3.6.1.4.1.37950.1.1.6.1.4.7.1.1
		-- 1.3.6.1.4.1.37950.1.1.6.1.4.7.1.1
		gOnuUpStatusPonInx OBJECT-TYPE
			SYNTAX Integer32 (1..16)
			MAX-ACCESS read-only
			STATUS current
			DESCRIPTION
				"Description."
			::= { gOnuUpStatusEntry 1 }

		
--  1.3.6.1.4.1.37950.1.1.6.1.4.7.1.2
		-- 1.3.6.1.4.1.37950.1.1.6.1.4.7.1.2
		gOnuUpStatusOnuInx OBJECT-TYPE
			SYNTAX Integer32 (1..128)
			MAX-ACCESS read-only
			STATUS current
			DESCRIPTION
				"Description."
			::= { gOnuUpStatusEntry 2 }

		
--  1.3.6.1.4.1.37950.1.1.6.1.4.7.1.3
		-- 1.3.6.1.4.1.37950.1.1.6.1.4.7.1.3
		gOnuUpStatusAction OBJECT-TYPE
			SYNTAX INTEGER
				{
				update(1),
				active(2),
				commit(3),
				update-and-reboot(4),
				quick_active(6)
				}
			MAX-ACCESS read-only
			STATUS current
			DESCRIPTION
				"Description."
			::= { gOnuUpStatusEntry 3 }

		
--  1.3.6.1.4.1.37950.1.1.6.1.4.7.1.4
		-- 1.3.6.1.4.1.37950.1.1.6.1.4.7.1.4
		gOnuUpStatusSta OBJECT-TYPE
			SYNTAX OCTET STRING
			MAX-ACCESS read-only
			STATUS current
			DESCRIPTION
				"Description."
			::= { gOnuUpStatusEntry 4 }

		
--  1.3.6.1.4.1.37950.1.1.6.1.4.7.1.5
		-- 1.3.6.1.4.1.37950.1.1.6.1.4.7.1.5
		gOnuUpStatusProgress OBJECT-TYPE
			SYNTAX OCTET STRING
			MAX-ACCESS read-only
			STATUS current
			DESCRIPTION
				"Description."
			::= { gOnuUpStatusEntry 5 }

		
--  1.3.6.1.4.1.37950.1.1.6.1.4.7.1.6
		-- 1.3.6.1.4.1.37950.1.1.6.1.4.7.1.6
		gOnuUpStatusFailreason OBJECT-TYPE
			SYNTAX OCTET STRING
			MAX-ACCESS read-only
			STATUS current
			DESCRIPTION
				"Description."
			::= { gOnuUpStatusEntry 6 }

		
--  1.3.6.1.4.1.37950.1.1.6.1.4.7.1.7
		-- 1.3.6.1.4.1.37950.1.1.6.1.4.7.1.7
		gOnuUpStatusCommitTime OBJECT-TYPE
			SYNTAX OCTET STRING
			MAX-ACCESS read-only
			STATUS current
			DESCRIPTION
				"Description."
			::= { gOnuUpStatusEntry 7 }

		
--  1.3.6.1.4.1.37950.1.1.6.1.4.8
		-- 1.3.6.1.4.1.37950.1.1.6.1.4.8
		gOnuUpAutoStatusTable OBJECT-TYPE
			SYNTAX SEQUENCE OF GOnuUpAutoStatusEntry
			MAX-ACCESS not-accessible
			STATUS current
			DESCRIPTION
				"Description."
			::= { gOnuUpgrade 8 }

		
--  1.3.6.1.4.1.37950.1.1.6.1.4.8.1
		-- 1.3.6.1.4.1.37950.1.1.6.1.4.8.1
		gOnuUpAutoStatusEntry OBJECT-TYPE
			SYNTAX GOnuUpAutoStatusEntry
			MAX-ACCESS not-accessible
			STATUS current
			DESCRIPTION
				"Description."
			INDEX { gOnuUpAutoStatusPONInx, gOnuUpAutoStatusONUInx }
			::= { gOnuUpAutoStatusTable 1 }

		
		GOnuUpAutoStatusEntry ::=
			SEQUENCE { 
				gOnuUpAutoStatusPONInx
					Integer32,
				gOnuUpAutoStatusONUInx
					Integer32,
				gOnuUpAutoStatusSta
					OCTET STRING,
				gOnuUpAutoStatusProgress
					OCTET STRING,
				gOnuUpAutoStatusFailreason
					OCTET STRING
			 }

--  1.3.6.1.4.1.37950.1.1.6.1.4.8.1.1
		-- 1.3.6.1.4.1.37950.1.1.6.1.4.8.1.1
		gOnuUpAutoStatusPONInx OBJECT-TYPE
			SYNTAX Integer32
			MAX-ACCESS read-write
			STATUS current
			DESCRIPTION
				"Description."
			::= { gOnuUpAutoStatusEntry 1 }

		
--  1.3.6.1.4.1.37950.1.1.6.1.4.8.1.2
		-- 1.3.6.1.4.1.37950.1.1.6.1.4.8.1.2
		gOnuUpAutoStatusONUInx OBJECT-TYPE
			SYNTAX Integer32
			MAX-ACCESS read-write
			STATUS current
			DESCRIPTION
				"Description."
			::= { gOnuUpAutoStatusEntry 2 }

		
--  1.3.6.1.4.1.37950.1.1.6.1.4.8.1.3
		-- 1.3.6.1.4.1.37950.1.1.6.1.4.8.1.3
		gOnuUpAutoStatusSta OBJECT-TYPE
			SYNTAX OCTET STRING
			MAX-ACCESS read-write
			STATUS current
			DESCRIPTION
				"Description."
			::= { gOnuUpAutoStatusEntry 3 }

		
--  1.3.6.1.4.1.37950.1.1.6.1.4.8.1.4
		-- 1.3.6.1.4.1.37950.1.1.6.1.4.8.1.4
		gOnuUpAutoStatusProgress OBJECT-TYPE
			SYNTAX OCTET STRING
			MAX-ACCESS read-write
			STATUS current
			DESCRIPTION
				"Description."
			::= { gOnuUpAutoStatusEntry 4 }

		
--  1.3.6.1.4.1.37950.1.1.6.1.4.8.1.5
		-- 1.3.6.1.4.1.37950.1.1.6.1.4.8.1.5
		gOnuUpAutoStatusFailreason OBJECT-TYPE
			SYNTAX OCTET STRING
			MAX-ACCESS read-write
			STATUS current
			DESCRIPTION
				"Description."
			::= { gOnuUpAutoStatusEntry 5 }

		
--  1.3.6.1.4.1.37950.1.1.6.1.4.9
		-- 1.3.6.1.4.1.37950.1.1.6.1.4.9
		gOnuUpStatusCntTable OBJECT-TYPE
			SYNTAX SEQUENCE OF GOnuUpStatusCntEntry
			MAX-ACCESS not-accessible
			STATUS current
			DESCRIPTION
				"Description."
			::= { gOnuUpgrade 9 }

		
--  1.3.6.1.4.1.37950.1.1.6.1.4.9.1
		-- 1.3.6.1.4.1.37950.1.1.6.1.4.9.1
		gOnuUpStatusCntEntry OBJECT-TYPE
			SYNTAX GOnuUpStatusCntEntry
			MAX-ACCESS not-accessible
			STATUS current
			DESCRIPTION
				"Description."
			INDEX { gOnuUpStatusCntTotal }
			::= { gOnuUpStatusCntTable 1 }

		
		GOnuUpStatusCntEntry ::=
			SEQUENCE { 
				gOnuUpStatusCntTotal
					Integer32,
				gOnuUpStatusCntValid
					Integer32,
				gOnuUpStatusCntWaiting
					Integer32,
				gOnuUpStatusCntRunning
					Integer32,
				gOnuUpStatusCntFinish
					Integer32
			 }

--  1.3.6.1.4.1.37950.1.1.6.1.4.9.1.1
		-- 1.3.6.1.4.1.37950.1.1.6.1.4.9.1.1
		gOnuUpStatusCntTotal OBJECT-TYPE
			SYNTAX Integer32
			MAX-ACCESS read-write
			STATUS current
			DESCRIPTION
				"Description."
			::= { gOnuUpStatusCntEntry 1 }

		
--  1.3.6.1.4.1.37950.1.1.6.1.4.9.1.2
		-- 1.3.6.1.4.1.37950.1.1.6.1.4.9.1.2
		gOnuUpStatusCntValid OBJECT-TYPE
			SYNTAX Integer32
			MAX-ACCESS read-write
			STATUS current
			DESCRIPTION
				"Description."
			::= { gOnuUpStatusCntEntry 2 }

		
--  1.3.6.1.4.1.37950.1.1.6.1.4.9.1.3
		-- 1.3.6.1.4.1.37950.1.1.6.1.4.9.1.3
		gOnuUpStatusCntWaiting OBJECT-TYPE
			SYNTAX Integer32
			MAX-ACCESS read-write
			STATUS current
			DESCRIPTION
				"Description."
			::= { gOnuUpStatusCntEntry 3 }

		
--  1.3.6.1.4.1.37950.1.1.6.1.4.9.1.4
		-- 1.3.6.1.4.1.37950.1.1.6.1.4.9.1.4
		gOnuUpStatusCntRunning OBJECT-TYPE
			SYNTAX Integer32
			MAX-ACCESS read-write
			STATUS current
			DESCRIPTION
				"Description."
			::= { gOnuUpStatusCntEntry 4 }

		
--  1.3.6.1.4.1.37950.1.1.6.1.4.9.1.5
		-- 1.3.6.1.4.1.37950.1.1.6.1.4.9.1.5
		gOnuUpStatusCntFinish OBJECT-TYPE
			SYNTAX Integer32
			MAX-ACCESS read-write
			STATUS current
			DESCRIPTION
				"Description."
			::= { gOnuUpStatusCntEntry 5 }

		
--  1.3.6.1.4.1.37950.1.1.6.1.4.10
		-- 1.3.6.1.4.1.37950.1.1.6.1.4.10
		gOnuUpAutoStatusCntTable OBJECT-TYPE
			SYNTAX SEQUENCE OF GOnuUpAutoStatusCntEntry
			MAX-ACCESS not-accessible
			STATUS current
			DESCRIPTION
				"Description."
			::= { gOnuUpgrade 10 }

		
--  1.3.6.1.4.1.37950.1.1.6.1.4.10.1
		-- 1.3.6.1.4.1.37950.1.1.6.1.4.10.1
		gOnuUpAutoStatusCntEntry OBJECT-TYPE
			SYNTAX GOnuUpAutoStatusCntEntry
			MAX-ACCESS not-accessible
			STATUS current
			DESCRIPTION
				"Description."
			INDEX { gOnuUpAutoStatusCntTotal }
			::= { gOnuUpAutoStatusCntTable 1 }

		
		GOnuUpAutoStatusCntEntry ::=
			SEQUENCE { 
				gOnuUpAutoStatusCntTotal
					Integer32,
				gOnuUpAutoStatusCntWaiting
					Integer32,
				gOnuUpAutoStatusCntRunning
					Integer32,
				gOnuUpAutoStatusCntFinish
					Integer32
			 }

--  1.3.6.1.4.1.37950.1.1.6.1.4.10.1.1
		-- 1.3.6.1.4.1.37950.1.1.6.1.4.10.1.1
		gOnuUpAutoStatusCntTotal OBJECT-TYPE
			SYNTAX Integer32
			MAX-ACCESS read-write
			STATUS current
			DESCRIPTION
				"Description."
			::= { gOnuUpAutoStatusCntEntry 1 }

		
--  1.3.6.1.4.1.37950.1.1.6.1.4.10.1.2
		-- 1.3.6.1.4.1.37950.1.1.6.1.4.10.1.2
		gOnuUpAutoStatusCntWaiting OBJECT-TYPE
			SYNTAX Integer32
			MAX-ACCESS read-write
			STATUS current
			DESCRIPTION
				"Description."
			::= { gOnuUpAutoStatusCntEntry 2 }

		
--  1.3.6.1.4.1.37950.1.1.6.1.4.10.1.3
		-- 1.3.6.1.4.1.37950.1.1.6.1.4.10.1.3
		gOnuUpAutoStatusCntRunning OBJECT-TYPE
			SYNTAX Integer32
			MAX-ACCESS read-write
			STATUS current
			DESCRIPTION
				"Description."
			::= { gOnuUpAutoStatusCntEntry 3 }

		
--  1.3.6.1.4.1.37950.1.1.6.1.4.10.1.4
		-- 1.3.6.1.4.1.37950.1.1.6.1.4.10.1.4
		gOnuUpAutoStatusCntFinish OBJECT-TYPE
			SYNTAX Integer32
			MAX-ACCESS read-write
			STATUS current
			DESCRIPTION
				"Description."
			::= { gOnuUpAutoStatusCntEntry 4 }

		
--  1.3.6.1.4.1.37950.1.1.6.1.4.11
		-- 1.3.6.1.4.1.37950.1.1.6.1.4.11
		gOnuUpAutoStatusAtion OBJECT IDENTIFIER ::= { gOnuUpgrade 11 }

		
--  1.3.6.1.4.1.37950.1.1.6.1.4.11.1
		-- 1.3.6.1.4.1.37950.1.1.6.1.4.11.1
		gOnuUpAutoStatusPonInx OBJECT-TYPE
			SYNTAX Integer32
			MAX-ACCESS read-write
			STATUS current
			DESCRIPTION
				"Description."
			::= { gOnuUpAutoStatusAtion 1 }

		
--  1.3.6.1.4.1.37950.1.1.6.1.4.11.2
		-- 1.3.6.1.4.1.37950.1.1.6.1.4.11.2
		gOnuUpAutoStatusOnuInx OBJECT-TYPE
			SYNTAX Integer32
			MAX-ACCESS read-write
			STATUS current
			DESCRIPTION
				"Description."
			::= { gOnuUpAutoStatusAtion 2 }

		
--  1.3.6.1.4.1.37950.1.1.6.1.4.11.3
		-- 1.3.6.1.4.1.37950.1.1.6.1.4.11.3
		gOnuUpAutoStatusDR OBJECT-TYPE
			SYNTAX INTEGER
				{
				delete(1),
				retry(2),
				clean(3)
				}
			MAX-ACCESS read-write
			STATUS current
			DESCRIPTION
				"Description."
			::= { gOnuUpAutoStatusAtion 3 }

		
--  1.3.6.1.4.1.37950.1.1.6.1.5
		-- 1.3.6.1.4.1.37950.1.1.6.1.5
		gRogueOnu OBJECT IDENTIFIER ::= { v1600gOnu 5 }

		
--  1.3.6.1.4.1.37950.1.1.6.1.5.1
		-- 1.3.6.1.4.1.37950.1.1.6.1.5.1
		gRogueOnuCfg OBJECT IDENTIFIER ::= { gRogueOnu 1 }

		
--  1.3.6.1.4.1.37950.1.1.6.1.5.1.1
		-- 1.3.6.1.4.1.37950.1.1.6.1.5.1.1
		gRogueOnuDetectState OBJECT-TYPE
			SYNTAX INTEGER
				{
				disable(0),
				enable(1)
				}
			MAX-ACCESS read-write
			STATUS current
			DESCRIPTION
				"Description."
			::= { gRogueOnuCfg 1 }

		
--  1.3.6.1.4.1.37950.1.1.6.1.5.1.2
		-- 1.3.6.1.4.1.37950.1.1.6.1.5.1.2
		gRogueOnuLocateState OBJECT-TYPE
			SYNTAX INTEGER
				{
				disable(0),
				enable(1)
				}
			MAX-ACCESS read-write
			STATUS current
			DESCRIPTION
				"Description."
			::= { gRogueOnuCfg 2 }

		
--  1.3.6.1.4.1.37950.1.1.6.1.5.1.3
		-- 1.3.6.1.4.1.37950.1.1.6.1.5.1.3
		gRogueOnuAutoShutdown OBJECT-TYPE
			SYNTAX INTEGER
				{
				disable(0),
				enable(1)
				}
			MAX-ACCESS read-write
			STATUS current
			DESCRIPTION
				"Description."
			::= { gRogueOnuCfg 3 }

		
--  1.3.6.1.4.1.37950.1.1.6.1.5.1.4
		-- 1.3.6.1.4.1.37950.1.1.6.1.5.1.4
		gRogueOnuControlMode OBJECT-TYPE
			SYNTAX INTEGER
				{
				private(0),
				itu-t(1),
				both(2)
				}
			MAX-ACCESS read-write
			STATUS current
			DESCRIPTION
				"Description."
			::= { gRogueOnuCfg 4 }

		
--  1.3.6.1.4.1.37950.1.1.6.1.5.1.5
		-- 1.3.6.1.4.1.37950.1.1.6.1.5.1.5
		gRogueOnuAction OBJECT-TYPE
			SYNTAX INTEGER { commit(1) }
			MAX-ACCESS read-write
			STATUS current
			DESCRIPTION
				"Description."
			::= { gRogueOnuCfg 5 }

		
--  1.3.6.1.4.1.37950.1.1.6.1.5.2
		-- 1.3.6.1.4.1.37950.1.1.6.1.5.2
		gRogueOnuTable OBJECT-TYPE
			SYNTAX SEQUENCE OF GRogueOnuEntry
			MAX-ACCESS not-accessible
			STATUS current
			DESCRIPTION
				"Description."
			::= { gRogueOnu 2 }

		
--  1.3.6.1.4.1.37950.1.1.6.1.5.2.1
		-- 1.3.6.1.4.1.37950.1.1.6.1.5.2.1
		gRogueOnuEntry OBJECT-TYPE
			SYNTAX GRogueOnuEntry
			MAX-ACCESS not-accessible
			STATUS current
			DESCRIPTION
				"Description."
			INDEX { gRogueOnuInfoDetectState }
			::= { gRogueOnuTable 1 }

		
		GRogueOnuEntry ::=
			SEQUENCE { 
				gRogueOnuInfoDetectState
					INTEGER,
				gRogueOnuInfoLocateState
					INTEGER,
				gRogueOnuInfoAutoShutDown
					INTEGER,
				gRogueOnuInfoControlMode
					INTEGER
			 }

--  1.3.6.1.4.1.37950.1.1.6.1.5.2.1.1
		-- 1.3.6.1.4.1.37950.1.1.6.1.5.2.1.1
		gRogueOnuInfoDetectState OBJECT-TYPE
			SYNTAX INTEGER
				{
				disable(0),
				enable(1)
				}
			MAX-ACCESS read-only
			STATUS current
			DESCRIPTION
				"Description."
			::= { gRogueOnuEntry 1 }

		
--  1.3.6.1.4.1.37950.1.1.6.1.5.2.1.2
		-- 1.3.6.1.4.1.37950.1.1.6.1.5.2.1.2
		gRogueOnuInfoLocateState OBJECT-TYPE
			SYNTAX INTEGER
				{
				disable(0),
				enable(1)
				}
			MAX-ACCESS read-only
			STATUS current
			DESCRIPTION
				"Description."
			::= { gRogueOnuEntry 2 }

		
--  1.3.6.1.4.1.37950.1.1.6.1.5.2.1.3
		-- 1.3.6.1.4.1.37950.1.1.6.1.5.2.1.3
		gRogueOnuInfoAutoShutDown OBJECT-TYPE
			SYNTAX INTEGER
				{
				disable(0),
				enable(1)
				}
			MAX-ACCESS read-only
			STATUS current
			DESCRIPTION
				"Description."
			::= { gRogueOnuEntry 3 }

		
--  1.3.6.1.4.1.37950.1.1.6.1.5.2.1.4
		-- 1.3.6.1.4.1.37950.1.1.6.1.5.2.1.4
		gRogueOnuInfoControlMode OBJECT-TYPE
			SYNTAX INTEGER
				{
				private(0),
				itu-t(1),
				both(2)
				}
			MAX-ACCESS read-only
			STATUS current
			DESCRIPTION
				"Description."
			::= { gRogueOnuEntry 4 }

		
--  1.3.6.1.4.1.37950.1.1.6.1.5.3
		-- 1.3.6.1.4.1.37950.1.1.6.1.5.3
		gRogueOnuListTable OBJECT-TYPE
			SYNTAX SEQUENCE OF GRogueOnuListEntry
			MAX-ACCESS not-accessible
			STATUS current
			DESCRIPTION
				"Description."
			::= { gRogueOnu 3 }

		
--  1.3.6.1.4.1.37950.1.1.6.1.5.3.1
		-- 1.3.6.1.4.1.37950.1.1.6.1.5.3.1
		gRogueOnuListEntry OBJECT-TYPE
			SYNTAX GRogueOnuListEntry
			MAX-ACCESS not-accessible
			STATUS current
			DESCRIPTION
				"Description."
			INDEX { gRogueOnuListPonInx, gRogueOnuListOnuInx }
			::= { gRogueOnuListTable 1 }

		
		GRogueOnuListEntry ::=
			SEQUENCE { 
				gRogueOnuListPonInx
					INTEGER,
				gRogueOnuListOnuInx
					INTEGER,
				gRogueOnuListKeywords
					OCTET STRING,
				gRogueOnuListTime
					OCTET STRING,
				gRogueOnuListState
					OCTET STRING
			 }

--  1.3.6.1.4.1.37950.1.1.6.1.5.3.1.1
		-- 1.3.6.1.4.1.37950.1.1.6.1.5.3.1.1
		gRogueOnuListPonInx OBJECT-TYPE
			SYNTAX INTEGER
			MAX-ACCESS read-write
			STATUS current
			DESCRIPTION
				"Description."
			::= { gRogueOnuListEntry 1 }

		
--  1.3.6.1.4.1.37950.1.1.6.1.5.3.1.2
		-- 1.3.6.1.4.1.37950.1.1.6.1.5.3.1.2
		gRogueOnuListOnuInx OBJECT-TYPE
			SYNTAX INTEGER
			MAX-ACCESS read-write
			STATUS current
			DESCRIPTION
				"Description."
			::= { gRogueOnuListEntry 2 }

		
--  1.3.6.1.4.1.37950.1.1.6.1.5.3.1.3
		-- 1.3.6.1.4.1.37950.1.1.6.1.5.3.1.3
		gRogueOnuListKeywords OBJECT-TYPE
			SYNTAX OCTET STRING
			MAX-ACCESS read-write
			STATUS current
			DESCRIPTION
				"Description."
			::= { gRogueOnuListEntry 3 }

		
--  1.3.6.1.4.1.37950.1.1.6.1.5.3.1.4
		-- 1.3.6.1.4.1.37950.1.1.6.1.5.3.1.4
		gRogueOnuListTime OBJECT-TYPE
			SYNTAX OCTET STRING
			MAX-ACCESS read-write
			STATUS current
			DESCRIPTION
				"Description."
			::= { gRogueOnuListEntry 4 }

		
--  1.3.6.1.4.1.37950.1.1.6.1.5.3.1.5
		-- 1.3.6.1.4.1.37950.1.1.6.1.5.3.1.5
		gRogueOnuListState OBJECT-TYPE
			SYNTAX OCTET STRING
			MAX-ACCESS read-write
			STATUS current
			DESCRIPTION
				"Description."
			::= { gRogueOnuListEntry 5 }

		
--  1.3.6.1.4.1.37950.1.1.6.1.5.4
		-- 1.3.6.1.4.1.37950.1.1.6.1.5.4
		gxbRogueOnuCfg OBJECT IDENTIFIER ::= { gRogueOnu 4 }

		
--  1.3.6.1.4.1.37950.1.1.6.1.5.4.1
		-- 1.3.6.1.4.1.37950.1.1.6.1.5.4.1
		gxbRogueOnuPon OBJECT-TYPE
			SYNTAX Integer32
			MAX-ACCESS read-write
			STATUS current
			DESCRIPTION
				"Description."
			::= { gxbRogueOnuCfg 1 }

		
--  1.3.6.1.4.1.37950.1.1.6.1.5.4.2
		-- 1.3.6.1.4.1.37950.1.1.6.1.5.4.2
		gxbRogueOnuDetectState OBJECT-TYPE
			SYNTAX INTEGER
				{
				disable(1),
				enable(2)
				}
			MAX-ACCESS read-write
			STATUS current
			DESCRIPTION
				"Description."
			::= { gxbRogueOnuCfg 2 }

		
--  1.3.6.1.4.1.37950.1.1.6.1.5.4.3
		-- 1.3.6.1.4.1.37950.1.1.6.1.5.4.3
		gxbRogueOnuMeasurement OBJECT-TYPE
			SYNTAX INTEGER
				{
				silent(1),
				cut_off(2)
				}
			MAX-ACCESS read-write
			STATUS current
			DESCRIPTION
				"Description."
			::= { gxbRogueOnuCfg 3 }

		
--  1.3.6.1.4.1.37950.1.1.6.1.5.4.4
		-- 1.3.6.1.4.1.37950.1.1.6.1.5.4.4
		gxbRogueOnuAutoShutdown OBJECT-TYPE
			SYNTAX INTEGER
				{
				disable(0),
				enable(1)
				}
			MAX-ACCESS read-write
			STATUS current
			DESCRIPTION
				"Description."
			::= { gxbRogueOnuCfg 4 }

		
--  1.3.6.1.4.1.37950.1.1.6.1.5.4.5
		-- 1.3.6.1.4.1.37950.1.1.6.1.5.4.5
		gxbRogueOnuAlgorithm OBJECT-TYPE
			SYNTAX INTEGER { early_rogue_detection(0) }
			MAX-ACCESS read-write
			STATUS current
			DESCRIPTION
				"Description."
			::= { gxbRogueOnuCfg 5 }

		
--  1.3.6.1.4.1.37950.1.1.6.1.5.4.6
		-- 1.3.6.1.4.1.37950.1.1.6.1.5.4.6
		gxbRogueOnuAction OBJECT-TYPE
			SYNTAX INTEGER { commit(0) }
			MAX-ACCESS read-write
			STATUS current
			DESCRIPTION
				"Description."
			::= { gxbRogueOnuCfg 6 }

		
--    1.3.6.1.4.1.37950.1.1.6.1.5.4.7
-- 1.3.6.1.4.1.37950.1.1.6.1.5.4.7
-- 1.3.6.1.4.1.37950.1.1.6.1.5.4.7
		-- 1.3.6.1.4.1.37950.1.1.6.1.5.4.7
		gxbRogueOnuAllocType OBJECT-TYPE
			SYNTAX INTEGER
				{
				Unused(0),
				Previously-used(1),
				All(2)
				}
			MAX-ACCESS read-write
			STATUS current
			DESCRIPTION
				"Description."
			::= { gxbRogueOnuCfg 7 }

		
--    1.3.6.1.4.1.37950.1.1.6.1.5.4.8
-- 1.3.6.1.4.1.37950.1.1.6.1.5.4.8
-- 1.3.6.1.4.1.37950.1.1.6.1.5.4.8
		-- 1.3.6.1.4.1.37950.1.1.6.1.5.4.8
		gxbRogueOnuShutdownType OBJECT-TYPE
			SYNTAX INTEGER
				{
				deactivate(0),
				reboot(1),
				disable(2)
				}
			MAX-ACCESS read-write
			STATUS current
			DESCRIPTION
				"Description."
			::= { gxbRogueOnuCfg 8 }

		
--  1.3.6.1.4.1.37950.1.1.6.1.5.5
		-- 1.3.6.1.4.1.37950.1.1.6.1.5.5
		gxbRogueOnuTable OBJECT-TYPE
			SYNTAX SEQUENCE OF GxbRogueOnuEntry
			MAX-ACCESS not-accessible
			STATUS current
			DESCRIPTION
				"Description."
			::= { gRogueOnu 5 }

		
--  1.3.6.1.4.1.37950.1.1.6.1.5.5.1
		-- 1.3.6.1.4.1.37950.1.1.6.1.5.5.1
		gxbRogueOnuEntry OBJECT-TYPE
			SYNTAX GxbRogueOnuEntry
			MAX-ACCESS not-accessible
			STATUS current
			DESCRIPTION
				"Description."
			INDEX { gxbRogueOnuPonS }
			::= { gxbRogueOnuTable 1 }

		
		GxbRogueOnuEntry ::=
			SEQUENCE { 
				gxbRogueOnuPonS
					Integer32,
				gxbRogueOnuDetectStateS
					INTEGER,
				gxbRogueOnuMeasurementS
					INTEGER,
				gxbRogueOnuAutoShutdownS
					INTEGER,
				gxbRogueOnuAlgorithmS
					INTEGER,
				gxbRogueOnuAllocTypeS
					INTEGER,
				gxbRogueOnuShutdownTypeS
					INTEGER
			 }

--  1.3.6.1.4.1.37950.1.1.6.1.5.5.1.1
		-- 1.3.6.1.4.1.37950.1.1.6.1.5.5.1.1
		gxbRogueOnuPonS OBJECT-TYPE
			SYNTAX Integer32
			MAX-ACCESS read-write
			STATUS current
			DESCRIPTION
				"Description."
			::= { gxbRogueOnuEntry 1 }

		
--  1.3.6.1.4.1.37950.1.1.6.1.5.5.1.2
		-- 1.3.6.1.4.1.37950.1.1.6.1.5.5.1.2
		gxbRogueOnuDetectStateS OBJECT-TYPE
			SYNTAX INTEGER
				{
				disable(1),
				enable(2)
				}
			MAX-ACCESS read-write
			STATUS current
			DESCRIPTION
				"Description."
			::= { gxbRogueOnuEntry 2 }

		
--  1.3.6.1.4.1.37950.1.1.6.1.5.5.1.3
		-- 1.3.6.1.4.1.37950.1.1.6.1.5.5.1.3
		gxbRogueOnuMeasurementS OBJECT-TYPE
			SYNTAX INTEGER
				{
				silent(1),
				cut_off(2)
				}
			MAX-ACCESS read-write
			STATUS current
			DESCRIPTION
				"Description."
			::= { gxbRogueOnuEntry 3 }

		
--  1.3.6.1.4.1.37950.1.1.6.1.5.5.1.4
		-- 1.3.6.1.4.1.37950.1.1.6.1.5.5.1.4
		gxbRogueOnuAutoShutdownS OBJECT-TYPE
			SYNTAX INTEGER
				{
				disable(0),
				enable(1)
				}
			MAX-ACCESS read-write
			STATUS current
			DESCRIPTION
				"Description."
			::= { gxbRogueOnuEntry 4 }

		
--  1.3.6.1.4.1.37950.1.1.6.1.5.5.1.5
		-- 1.3.6.1.4.1.37950.1.1.6.1.5.5.1.5
		gxbRogueOnuAlgorithmS OBJECT-TYPE
			SYNTAX INTEGER
				{
				early_detection(0),
				extend_guard(1)
				}
			MAX-ACCESS read-write
			STATUS current
			DESCRIPTION
				"Description."
			::= { gxbRogueOnuEntry 5 }

		
--    1.3.6.1.4.1.37950.1.1.6.1.5.5.1.6
-- 1.3.6.1.4.1.37950.1.1.6.1.5.5.1.6
-- 1.3.6.1.4.1.37950.1.1.6.1.5.5.1.6
		-- 1.3.6.1.4.1.37950.1.1.6.1.5.5.1.6
		gxbRogueOnuAllocTypeS OBJECT-TYPE
			SYNTAX INTEGER
				{
				Unused(0),
				Previously-used(1),
				All(2)
				}
			MAX-ACCESS read-write
			STATUS current
			DESCRIPTION
				"Description."
			::= { gxbRogueOnuEntry 6 }

		
--    1.3.6.1.4.1.37950.1.1.6.1.5.5.1.7
-- 1.3.6.1.4.1.37950.1.1.6.1.5.5.1.7
-- 1.3.6.1.4.1.37950.1.1.6.1.5.5.1.7
		-- 1.3.6.1.4.1.37950.1.1.6.1.5.5.1.7
		gxbRogueOnuShutdownTypeS OBJECT-TYPE
			SYNTAX INTEGER
				{
				deactivate(0),
				reboot(1),
				disable(2)
				}
			MAX-ACCESS read-write
			STATUS current
			DESCRIPTION
				"Description."
			::= { gxbRogueOnuEntry 7 }

		
--  1.3.6.1.4.1.37950.1.1.6.1.6
		-- 1.3.6.1.4.1.37950.1.1.6.1.6
		gOnuPriCfg OBJECT IDENTIFIER ::= { v1600gOnu 6 }

		
--  1.3.6.1.4.1.37950.1.1.6.1.6.1
		-- 1.3.6.1.4.1.37950.1.1.6.1.6.1
		gOnuPriWanConn OBJECT IDENTIFIER ::= { gOnuPriCfg 1 }

		
--  1.3.6.1.4.1.37950.1.1.6.1.6.1.1
		-- 1.3.6.1.4.1.37950.1.1.6.1.6.1.1
		gOnuPriWanConnAdd OBJECT IDENTIFIER ::= { gOnuPriWanConn 1 }

		
--  1.3.6.1.4.1.37950.1.1.6.1.6.1.1.1
		-- 1.3.6.1.4.1.37950.1.1.6.1.6.1.1.1
		gOnuPriWanAddPon OBJECT-TYPE
			SYNTAX Integer32 (1..16)
			MAX-ACCESS read-write
			STATUS current
			DESCRIPTION
				"Description."
			::= { gOnuPriWanConnAdd 1 }

		
--  1.3.6.1.4.1.37950.1.1.6.1.6.1.1.2
		-- 1.3.6.1.4.1.37950.1.1.6.1.6.1.1.2
		gOnuPriWanAddOnu OBJECT-TYPE
			SYNTAX Integer32 (1..128)
			MAX-ACCESS read-write
			STATUS current
			DESCRIPTION
				"Description."
			::= { gOnuPriWanConnAdd 2 }

		
--  1.3.6.1.4.1.37950.1.1.6.1.6.1.1.3
		-- 1.3.6.1.4.1.37950.1.1.6.1.6.1.1.3
		gOnuPriWanConnType OBJECT-TYPE
			SYNTAX INTEGER
				{
				brige(0),
				route(1)
				}
			MAX-ACCESS read-write
			STATUS current
			DESCRIPTION
				"Description."
			::= { gOnuPriWanConnAdd 3 }

		
--  1.3.6.1.4.1.37950.1.1.6.1.6.1.1.4
		-- 1.3.6.1.4.1.37950.1.1.6.1.6.1.1.4
		gOnuPriWanConnAddAction OBJECT-TYPE
			SYNTAX INTEGER { add(1) }
			MAX-ACCESS read-write
			STATUS current
			DESCRIPTION
				"Description."
			::= { gOnuPriWanConnAdd 4 }

		
--  1.3.6.1.4.1.37950.1.1.6.1.6.1.2
		-- 1.3.6.1.4.1.37950.1.1.6.1.6.1.2
		gOnuPriWanConnDelete OBJECT IDENTIFIER ::= { gOnuPriWanConn 2 }

		
--  1.3.6.1.4.1.37950.1.1.6.1.6.1.2.1
		-- 1.3.6.1.4.1.37950.1.1.6.1.6.1.2.1
		gOnuPriWanDeletePonInx OBJECT-TYPE
			SYNTAX INTEGER (1..16)
			MAX-ACCESS read-write
			STATUS current
			DESCRIPTION
				"Description."
			::= { gOnuPriWanConnDelete 1 }

		
--  1.3.6.1.4.1.37950.1.1.6.1.6.1.2.2
		-- 1.3.6.1.4.1.37950.1.1.6.1.6.1.2.2
		gOnuPriWanDeleteOnuInx OBJECT-TYPE
			SYNTAX INTEGER (1..65535)
			MAX-ACCESS read-write
			STATUS current
			DESCRIPTION
				"Description."
			::= { gOnuPriWanConnDelete 2 }

		
--  1.3.6.1.4.1.37950.1.1.6.1.6.1.2.3
		-- 1.3.6.1.4.1.37950.1.1.6.1.6.1.2.3
		gOnuPriConnIndexD OBJECT-TYPE
			SYNTAX Integer32 (1..8)
			MAX-ACCESS read-write
			STATUS current
			DESCRIPTION
				"Description."
			::= { gOnuPriWanConnDelete 3 }

		
--  1.3.6.1.4.1.37950.1.1.6.1.6.1.2.4
		-- 1.3.6.1.4.1.37950.1.1.6.1.6.1.2.4
		gOnuPriConnDeleteAction OBJECT-TYPE
			SYNTAX INTEGER { delete(1) }
			MAX-ACCESS read-write
			STATUS current
			DESCRIPTION
				"Description."
			::= { gOnuPriWanConnDelete 4 }

		
--  1.3.6.1.4.1.37950.1.1.6.1.6.1.3
		-- 1.3.6.1.4.1.37950.1.1.6.1.6.1.3
		gOnuPriWanConnCfg OBJECT IDENTIFIER ::= { gOnuPriWanConn 3 }

		
--  1.3.6.1.4.1.37950.1.1.6.1.6.1.3.1
		-- 1.3.6.1.4.1.37950.1.1.6.1.6.1.3.1
		priConnPon OBJECT-TYPE
			SYNTAX INTEGER (1..16)
			MAX-ACCESS read-write
			STATUS current
			DESCRIPTION
				"Description."
			::= { gOnuPriWanConnCfg 1 }

		
--  1.3.6.1.4.1.37950.1.1.6.1.6.1.3.2
		-- 1.3.6.1.4.1.37950.1.1.6.1.6.1.3.2
		priConnOnu OBJECT-TYPE
			SYNTAX INTEGER (1..65535)
			MAX-ACCESS read-write
			STATUS current
			DESCRIPTION
				"Description."
			::= { gOnuPriWanConnCfg 2 }

		
--  1.3.6.1.4.1.37950.1.1.6.1.6.1.3.3
		-- 1.3.6.1.4.1.37950.1.1.6.1.6.1.3.3
		priConnIndex OBJECT-TYPE
			SYNTAX INTEGER (1..8)
			MAX-ACCESS read-write
			STATUS current
			DESCRIPTION
				"Description."
			::= { gOnuPriWanConnCfg 3 }

		
--  1.3.6.1.4.1.37950.1.1.6.1.6.1.3.4
		-- 1.3.6.1.4.1.37950.1.1.6.1.6.1.3.4
		priConnBindLan OBJECT-TYPE
			SYNTAX INTEGER (0..255)
			MAX-ACCESS read-write
			STATUS current
			DESCRIPTION
				"Description."
			::= { gOnuPriWanConnCfg 4 }

		
--  1.3.6.1.4.1.37950.1.1.6.1.6.1.3.5
		-- 1.3.6.1.4.1.37950.1.1.6.1.6.1.3.5
		priConnBindSsid OBJECT-TYPE
			SYNTAX INTEGER (0..255)
			MAX-ACCESS read-write
			STATUS current
			DESCRIPTION
				"Description."
			::= { gOnuPriWanConnCfg 5 }

		
--  1.3.6.1.4.1.37950.1.1.6.1.6.1.3.6
		-- 1.3.6.1.4.1.37950.1.1.6.1.6.1.3.6
		priWanMode OBJECT-TYPE
			SYNTAX INTEGER
				{
				internet(0),
				multicast(1),
				tr069(2),
				tr069_internet(3),
				tr069_voip(4),
				voip_internet(5),
				tr069_voip_internet(6),
				voip(7),
				other(100)
				}
			MAX-ACCESS read-write
			STATUS current
			DESCRIPTION
				"Description."
			::= { gOnuPriWanConnCfg 6 }

		
--  1.3.6.1.4.1.37950.1.1.6.1.6.1.3.7
		-- 1.3.6.1.4.1.37950.1.1.6.1.6.1.3.7
		priConnTypeCfg OBJECT-TYPE
			SYNTAX INTEGER
				{
				bridge(0),
				route(1)
				}
			MAX-ACCESS read-write
			STATUS current
			DESCRIPTION
				"Description."
			::= { gOnuPriWanConnCfg 7 }

		
--  1.3.6.1.4.1.37950.1.1.6.1.6.1.3.8
		-- 1.3.6.1.4.1.37950.1.1.6.1.6.1.3.8
		priConnNatEnable OBJECT-TYPE
			SYNTAX INTEGER
				{
				disable(0),
				enable(1)
				}
			MAX-ACCESS read-write
			STATUS current
			DESCRIPTION
				"Description."
			::= { gOnuPriWanConnCfg 8 }

		
--  1.3.6.1.4.1.37950.1.1.6.1.6.1.3.9
		-- 1.3.6.1.4.1.37950.1.1.6.1.6.1.3.9
		priConnModeCfg OBJECT-TYPE
			SYNTAX INTEGER
				{
				dhcp(0),
				static(1),
				pppoe(2)
				}
			MAX-ACCESS read-write
			STATUS current
			DESCRIPTION
				"Description."
			::= { gOnuPriWanConnCfg 9 }

		
--  1.3.6.1.4.1.37950.1.1.6.1.6.1.3.10
		-- 1.3.6.1.4.1.37950.1.1.6.1.6.1.3.10
		priConnIpAddress OBJECT-TYPE
			SYNTAX IpAddress
			MAX-ACCESS read-write
			STATUS current
			DESCRIPTION
				"Description."
			::= { gOnuPriWanConnCfg 10 }

		
--  1.3.6.1.4.1.37950.1.1.6.1.6.1.3.11
		-- 1.3.6.1.4.1.37950.1.1.6.1.6.1.3.11
		priConnIpMask OBJECT-TYPE
			SYNTAX IpAddress
			MAX-ACCESS read-write
			STATUS current
			DESCRIPTION
				"Description."
			::= { gOnuPriWanConnCfg 11 }

		
--  1.3.6.1.4.1.37950.1.1.6.1.6.1.3.12
		-- 1.3.6.1.4.1.37950.1.1.6.1.6.1.3.12
		priConnGateway OBJECT-TYPE
			SYNTAX IpAddress
			MAX-ACCESS read-write
			STATUS current
			DESCRIPTION
				"Description."
			::= { gOnuPriWanConnCfg 12 }

		
--  1.3.6.1.4.1.37950.1.1.6.1.6.1.3.13
		-- 1.3.6.1.4.1.37950.1.1.6.1.6.1.3.13
		priConnMasterDns OBJECT-TYPE
			SYNTAX IpAddress
			MAX-ACCESS read-write
			STATUS current
			DESCRIPTION
				"Description."
			::= { gOnuPriWanConnCfg 13 }

		
--  1.3.6.1.4.1.37950.1.1.6.1.6.1.3.14
		-- 1.3.6.1.4.1.37950.1.1.6.1.6.1.3.14
		priConnSlaveDns OBJECT-TYPE
			SYNTAX IpAddress
			MAX-ACCESS read-write
			STATUS current
			DESCRIPTION
				"Description."
			::= { gOnuPriWanConnCfg 14 }

		
--  1.3.6.1.4.1.37950.1.1.6.1.6.1.3.15
		-- 1.3.6.1.4.1.37950.1.1.6.1.6.1.3.15
		priConnPppoeProxy OBJECT-TYPE
			SYNTAX INTEGER
				{
				disable(0),
				enable(1)
				}
			MAX-ACCESS read-write
			STATUS current
			DESCRIPTION
				"Description."
			::= { gOnuPriWanConnCfg 15 }

		
--  1.3.6.1.4.1.37950.1.1.6.1.6.1.3.16
		-- 1.3.6.1.4.1.37950.1.1.6.1.6.1.3.16
		priConnPppoeUsername OBJECT-TYPE
			SYNTAX OCTET STRING
			MAX-ACCESS read-write
			STATUS current
			DESCRIPTION
				"Description."
			::= { gOnuPriWanConnCfg 16 }

		
--  1.3.6.1.4.1.37950.1.1.6.1.6.1.3.17
		-- 1.3.6.1.4.1.37950.1.1.6.1.6.1.3.17
		priConnPppoePassword OBJECT-TYPE
			SYNTAX OCTET STRING
			MAX-ACCESS read-write
			STATUS current
			DESCRIPTION
				"Description."
			::= { gOnuPriWanConnCfg 17 }

		
--  1.3.6.1.4.1.37950.1.1.6.1.6.1.3.18
		-- 1.3.6.1.4.1.37950.1.1.6.1.6.1.3.18
		priConnPppoeSerName OBJECT-TYPE
			SYNTAX OCTET STRING
			MAX-ACCESS read-write
			STATUS current
			DESCRIPTION
				"Description."
			::= { gOnuPriWanConnCfg 18 }

		
--  1.3.6.1.4.1.37950.1.1.6.1.6.1.3.19
		-- 1.3.6.1.4.1.37950.1.1.6.1.6.1.3.19
		priConnPppoeMode OBJECT-TYPE
			SYNTAX INTEGER
				{
				autoConnect(0),
				flowConnect(1)
				}
			MAX-ACCESS read-write
			STATUS current
			DESCRIPTION
				"Description."
			::= { gOnuPriWanConnCfg 19 }

		
--  1.3.6.1.4.1.37950.1.1.6.1.6.1.3.20
		-- 1.3.6.1.4.1.37950.1.1.6.1.6.1.3.20
		priConnQosEnable OBJECT-TYPE
			SYNTAX INTEGER
				{
				disable(0),
				enable(1)
				}
			MAX-ACCESS read-write
			STATUS current
			DESCRIPTION
				"Description."
			::= { gOnuPriWanConnCfg 20 }

		
--  1.3.6.1.4.1.37950.1.1.6.1.6.1.3.21
		-- 1.3.6.1.4.1.37950.1.1.6.1.6.1.3.21
		priConnVlanMode OBJECT-TYPE
			SYNTAX INTEGER
				{
				disable(0),
				enable(1)
				}
			MAX-ACCESS read-write
			STATUS current
			DESCRIPTION
				"Description."
			::= { gOnuPriWanConnCfg 21 }

		
--  1.3.6.1.4.1.37950.1.1.6.1.6.1.3.22
		-- 1.3.6.1.4.1.37950.1.1.6.1.6.1.3.22
		priConnVlanId OBJECT-TYPE
			SYNTAX Integer32 (0..4095)
			MAX-ACCESS read-write
			STATUS current
			DESCRIPTION
				"Description."
			::= { gOnuPriWanConnCfg 22 }

		
--  1.3.6.1.4.1.37950.1.1.6.1.6.1.3.23
		-- 1.3.6.1.4.1.37950.1.1.6.1.6.1.3.23
		priConnCos OBJECT-TYPE
			SYNTAX INTEGER (0..7)
			MAX-ACCESS read-write
			STATUS current
			DESCRIPTION
				"Description."
			::= { gOnuPriWanConnCfg 23 }

		
--  1.3.6.1.4.1.37950.1.1.6.1.6.1.3.24
		-- 1.3.6.1.4.1.37950.1.1.6.1.6.1.3.24
		priConnCfgAction OBJECT-TYPE
			SYNTAX INTEGER { commit(1) }
			MAX-ACCESS read-write
			STATUS current
			DESCRIPTION
				"Description."
			::= { gOnuPriWanConnCfg 24 }

		
--  1.3.6.1.4.1.37950.1.1.6.1.6.1.3.25
		-- 1.3.6.1.4.1.37950.1.1.6.1.6.1.3.25
		priConnMTU OBJECT-TYPE
			SYNTAX INTEGER (0 | 576..1500)
			MAX-ACCESS read-write
			STATUS current
			DESCRIPTION
				"Description."
			::= { gOnuPriWanConnCfg 25 }

		
--   1.3.6.1.4.1.37950.1.1.5.12.3.1.6.4
-- 1.3.6.1.4.1.37950.1.1.6.1.6.1.4
		-- 1.3.6.1.4.1.37950.1.1.6.1.6.1.4
		gOnuPriWanConnCommit OBJECT IDENTIFIER ::= { gOnuPriWanConn 4 }

		
--   1.3.6.1.4.1.37950.1.1.5.12.3.1.6.4.1
-- 1.3.6.1.4.1.37950.1.1.6.1.6.1.4.1
		-- 1.3.6.1.4.1.37950.1.1.6.1.6.1.4.1
		gOnuPriConnCommitPon OBJECT-TYPE
			SYNTAX INTEGER (1..16)
			MAX-ACCESS read-write
			STATUS current
			DESCRIPTION
				"Description."
			::= { gOnuPriWanConnCommit 1 }

		
--   1.3.6.1.4.1.37950.1.1.5.12.3.1.6.4.2
-- 1.3.6.1.4.1.37950.1.1.6.1.6.1.4.2
		-- 1.3.6.1.4.1.37950.1.1.6.1.6.1.4.2
		gOnuPriConnCommitOnu OBJECT-TYPE
			SYNTAX INTEGER (1..65535)
			MAX-ACCESS read-write
			STATUS current
			DESCRIPTION
				"Description."
			::= { gOnuPriWanConnCommit 2 }

		
--   1.3.6.1.4.1.37950.1.1.5.12.3.1.6.4.3
-- 1.3.6.1.4.1.37950.1.1.6.1.6.1.4.3
		-- 1.3.6.1.4.1.37950.1.1.6.1.6.1.4.3
		gOnuPriConnCommitAction OBJECT-TYPE
			SYNTAX INTEGER
				{
				commit(1),
				remove(2)
				}
			MAX-ACCESS read-write
			STATUS current
			DESCRIPTION
				"Description."
			::= { gOnuPriWanConnCommit 3 }

		
--  1.3.6.1.4.1.37950.1.1.6.1.6.2
		-- 1.3.6.1.4.1.37950.1.1.6.1.6.2
		gOnuPriDhcpServer OBJECT IDENTIFIER ::= { gOnuPriCfg 2 }

		
--  1.3.6.1.4.1.37950.1.1.6.1.6.2.1
		-- 1.3.6.1.4.1.37950.1.1.6.1.6.2.1
		gOnuPriDhcpServerPonInx OBJECT-TYPE
			SYNTAX Integer32 (1..16)
			MAX-ACCESS read-write
			STATUS current
			DESCRIPTION
				"Description."
			::= { gOnuPriDhcpServer 1 }

		
--  1.3.6.1.4.1.37950.1.1.6.1.6.2.2
		-- 1.3.6.1.4.1.37950.1.1.6.1.6.2.2
		gOnuPriDhcpServerOnuInx OBJECT-TYPE
			SYNTAX Integer32 (1..65525)
			MAX-ACCESS read-write
			STATUS current
			DESCRIPTION
				"Description."
			::= { gOnuPriDhcpServer 2 }

		
--  1.3.6.1.4.1.37950.1.1.6.1.6.2.3
		-- 1.3.6.1.4.1.37950.1.1.6.1.6.2.3
		gOnuPriDhcpLanIp OBJECT-TYPE
			SYNTAX IpAddress
			MAX-ACCESS read-write
			STATUS current
			DESCRIPTION
				"Description."
			::= { gOnuPriDhcpServer 3 }

		
--  1.3.6.1.4.1.37950.1.1.6.1.6.2.4
		-- 1.3.6.1.4.1.37950.1.1.6.1.6.2.4
		gOnuPriDhcpLanMask OBJECT-TYPE
			SYNTAX IpAddress
			MAX-ACCESS read-write
			STATUS current
			DESCRIPTION
				"Description."
			::= { gOnuPriDhcpServer 4 }

		
--  1.3.6.1.4.1.37950.1.1.6.1.6.2.5
		-- 1.3.6.1.4.1.37950.1.1.6.1.6.2.5
		gOnuPriDhcpEnable OBJECT-TYPE
			SYNTAX INTEGER
				{
				disable(0),
				enable(1),
				relay(2)
				}
			MAX-ACCESS read-write
			STATUS current
			DESCRIPTION
				"Description."
			::= { gOnuPriDhcpServer 5 }

		
--  1.3.6.1.4.1.37950.1.1.6.1.6.2.6
		-- 1.3.6.1.4.1.37950.1.1.6.1.6.2.6
		gOnuPriDhcpLease OBJECT-TYPE
			SYNTAX Unsigned32 (0..4294967295)
			MAX-ACCESS read-write
			STATUS current
			DESCRIPTION
				"Description."
			::= { gOnuPriDhcpServer 6 }

		
--  1.3.6.1.4.1.37950.1.1.6.1.6.2.7
		-- 1.3.6.1.4.1.37950.1.1.6.1.6.2.7
		gOnuPriDhcpBeginIp OBJECT-TYPE
			SYNTAX IpAddress
			MAX-ACCESS read-write
			STATUS current
			DESCRIPTION
				"Description."
			::= { gOnuPriDhcpServer 7 }

		
--  1.3.6.1.4.1.37950.1.1.6.1.6.2.8
		-- 1.3.6.1.4.1.37950.1.1.6.1.6.2.8
		gOnuPriDhcpEndIp OBJECT-TYPE
			SYNTAX IpAddress
			MAX-ACCESS read-write
			STATUS current
			DESCRIPTION
				"Description."
			::= { gOnuPriDhcpServer 8 }

		
--  1.3.6.1.4.1.37950.1.1.6.1.6.2.9
		-- 1.3.6.1.4.1.37950.1.1.6.1.6.2.9
		gOnuPriDhcpPoolType OBJECT-TYPE
			SYNTAX INTEGER
				{
				pc(0),
				camera(1),
				stb(2),
				ip_phone(3)
				}
			MAX-ACCESS read-write
			STATUS current
			DESCRIPTION
				"Description."
			::= { gOnuPriDhcpServer 9 }

		
--  1.3.6.1.4.1.37950.1.1.6.1.6.2.10
		-- 1.3.6.1.4.1.37950.1.1.6.1.6.2.10
		gOnuPriDhcpMasterDns OBJECT-TYPE
			SYNTAX IpAddress
			MAX-ACCESS read-write
			STATUS current
			DESCRIPTION
				"Description."
			::= { gOnuPriDhcpServer 10 }

		
--  1.3.6.1.4.1.37950.1.1.6.1.6.2.11
		-- 1.3.6.1.4.1.37950.1.1.6.1.6.2.11
		gOnuPriDhcpSlaveDns OBJECT-TYPE
			SYNTAX IpAddress
			MAX-ACCESS read-write
			STATUS current
			DESCRIPTION
				"Description."
			::= { gOnuPriDhcpServer 11 }

		
--  1.3.6.1.4.1.37950.1.1.6.1.6.2.12
		-- 1.3.6.1.4.1.37950.1.1.6.1.6.2.12
		gOnuPriDhcpGateway OBJECT-TYPE
			SYNTAX IpAddress
			MAX-ACCESS read-write
			STATUS current
			DESCRIPTION
				"Description."
			::= { gOnuPriDhcpServer 12 }

		
--  1.3.6.1.4.1.37950.1.1.6.1.6.2.13
		-- 1.3.6.1.4.1.37950.1.1.6.1.6.2.13
		gOnuPriDhcpRelayIp OBJECT-TYPE
			SYNTAX IpAddress
			MAX-ACCESS read-write
			STATUS current
			DESCRIPTION
				"Description."
			::= { gOnuPriDhcpServer 13 }

		
--  1.3.6.1.4.1.37950.1.1.6.1.6.2.14
		-- 1.3.6.1.4.1.37950.1.1.6.1.6.2.14
		gOnuPriDhcpAction OBJECT-TYPE
			SYNTAX INTEGER { commit(1) }
			MAX-ACCESS read-write
			STATUS current
			DESCRIPTION
				"Description."
			::= { gOnuPriDhcpServer 14 }

		
--  1.3.6.1.4.1.37950.1.1.6.1.6.2.15
		-- 1.3.6.1.4.1.37950.1.1.6.1.6.2.15
		gOnuPriDhcpDnsMode OBJECT-TYPE
			SYNTAX INTEGER
				{
				static(0),
				hgw_proxy(1),
				from_isp(2)
				}
			MAX-ACCESS read-write
			STATUS current
			DESCRIPTION
				"Description."
			::= { gOnuPriDhcpServer 15 }

		
--  1.3.6.1.4.1.37950.1.1.6.1.6.3
		-- 1.3.6.1.4.1.37950.1.1.6.1.6.3
		gOnuPriWifiSwitch OBJECT IDENTIFIER ::= { gOnuPriCfg 3 }

		
--  1.3.6.1.4.1.37950.1.1.6.1.6.3.1
		-- 1.3.6.1.4.1.37950.1.1.6.1.6.3.1
		priWifiSwitchPon OBJECT-TYPE
			SYNTAX INTEGER (1..16)
			MAX-ACCESS read-write
			STATUS current
			DESCRIPTION
				"Description."
			::= { gOnuPriWifiSwitch 1 }

		
--  1.3.6.1.4.1.37950.1.1.6.1.6.3.2
		-- 1.3.6.1.4.1.37950.1.1.6.1.6.3.2
		priWifiSwitchOnu OBJECT-TYPE
			SYNTAX INTEGER (1..65525)
			MAX-ACCESS read-write
			STATUS current
			DESCRIPTION
				"Description."
			::= { gOnuPriWifiSwitch 2 }

		
--  1.3.6.1.4.1.37950.1.1.6.1.6.3.3
		-- 1.3.6.1.4.1.37950.1.1.6.1.6.3.3
		priWifiSwitchNo OBJECT-TYPE
			SYNTAX INTEGER (1..2)
			MAX-ACCESS read-write
			STATUS current
			DESCRIPTION
				"Description."
			::= { gOnuPriWifiSwitch 3 }

		
--  1.3.6.1.4.1.37950.1.1.6.1.6.3.4
		-- 1.3.6.1.4.1.37950.1.1.6.1.6.3.4
		priWifiApModule OBJECT-TYPE
			SYNTAX INTEGER
				{
				disable(0),
				enable(1)
				}
			MAX-ACCESS read-write
			STATUS current
			DESCRIPTION
				"Description."
			::= { gOnuPriWifiSwitch 4 }

		
--  1.3.6.1.4.1.37950.1.1.6.1.6.3.5
		-- 1.3.6.1.4.1.37950.1.1.6.1.6.3.5
		priWifiCountry OBJECT-TYPE
			SYNTAX INTEGER
				{
				etsi(0),
				fcc(1),
				ic(2),
				spain(3),
				france(4),
				mkk(5),
				isreal(6),
				mkk2(7),
				mkk3(8),
				russian(9),
				cn(10),
				global(11),
				world-wide(12),
				mkk1(13),
				ncc(14)
				}
			MAX-ACCESS read-write
			STATUS current
			DESCRIPTION
				"Description."
			::= { gOnuPriWifiSwitch 5 }

		
--  1.3.6.1.4.1.37950.1.1.6.1.6.3.6
		-- 1.3.6.1.4.1.37950.1.1.6.1.6.3.6
		priWifiChannel OBJECT-TYPE
			SYNTAX Integer32
			MAX-ACCESS read-write
			STATUS current
			DESCRIPTION
				"Description."
			::= { gOnuPriWifiSwitch 6 }

		
--  1.3.6.1.4.1.37950.1.1.6.1.6.3.7
		-- 1.3.6.1.4.1.37950.1.1.6.1.6.3.7
		priWifiStandard OBJECT-TYPE
			SYNTAX INTEGER
				{
				s80211b(0),
				s80211g(1),
				s80211bg(2),
				s80211n(3),
				s80211bgn(4),
				s80211ac(5),
				s80211acA(6),
				s80211acN(7),
				s80211acAN(8),
				s80211acNAC(9),
				s80211acANAC(10),
				s80211acax(11),
				s80211acANACax(12),
				s80211ax(13),
				s80211bgnax(14),
				s80211gn(15)
				}
			MAX-ACCESS read-write
			STATUS current
			DESCRIPTION
				"Description."
			::= { gOnuPriWifiSwitch 7 }

		
--  1.3.6.1.4.1.37950.1.1.6.1.6.3.8
		-- 1.3.6.1.4.1.37950.1.1.6.1.6.3.8
		priWifiPower OBJECT-TYPE
			SYNTAX INTEGER (0..20)
			MAX-ACCESS read-write
			STATUS current
			DESCRIPTION
				"Description."
			::= { gOnuPriWifiSwitch 8 }

		
--  1.3.6.1.4.1.37950.1.1.6.1.6.3.9
		-- 1.3.6.1.4.1.37950.1.1.6.1.6.3.9
		priWifiSwitchAction OBJECT-TYPE
			SYNTAX INTEGER
				{
				commit(1),
				remove(2)
				}
			MAX-ACCESS read-write
			STATUS current
			DESCRIPTION
				"Description."
			::= { gOnuPriWifiSwitch 9 }

		
--  1.3.6.1.4.1.37950.1.1.6.1.6.3.10
		-- 1.3.6.1.4.1.37950.1.1.6.1.6.3.10
		priWifi2g4 OBJECT-TYPE
			SYNTAX INTEGER
				{
				not-support(0),
				support(1)
				}
			MAX-ACCESS read-only
			STATUS current
			DESCRIPTION
				"Description."
			::= { gOnuPriWifiSwitch 10 }

		
--  1.3.6.1.4.1.37950.1.1.6.1.6.3.11
		-- 1.3.6.1.4.1.37950.1.1.6.1.6.3.11
		priWifi5g OBJECT-TYPE
			SYNTAX INTEGER
				{
				not-support(0),
				support(1)
				}
			MAX-ACCESS read-only
			STATUS current
			DESCRIPTION
				"Description."
			::= { gOnuPriWifiSwitch 11 }

		
--  1.3.6.1.4.1.37950.1.1.6.1.6.3.12
		-- 1.3.6.1.4.1.37950.1.1.6.1.6.3.12
		priWifiChannelWidth OBJECT-TYPE
			SYNTAX INTEGER
				{
				s20MHz(0),
				s40MHz(1),
				s80MHz(2),
				s20_40MHz(3),
				s20_40_80MHz(4),
				s160MHz(5)
				}
			MAX-ACCESS read-write
			STATUS current
			DESCRIPTION
				"Description."
			::= { gOnuPriWifiSwitch 12 }

		
--  1.3.6.1.4.1.37950.1.1.6.1.6.3.13
		-- 1.3.6.1.4.1.37950.1.1.6.1.6.3.13
		priWifiEasyMeshStatus OBJECT-TYPE
			SYNTAX INTEGER
				{
				disable(0),
				enable(1)
				}
			MAX-ACCESS read-write
			STATUS current
			DESCRIPTION
				"Description."
			::= { gOnuPriWifiSwitch 13 }

		
--  1.3.6.1.4.1.37950.1.1.6.1.6.4
		-- 1.3.6.1.4.1.37950.1.1.6.1.6.4
		gOnuPriWifiSsid OBJECT IDENTIFIER ::= { gOnuPriCfg 4 }

		
--  1.3.6.1.4.1.37950.1.1.6.1.6.4.1
		-- 1.3.6.1.4.1.37950.1.1.6.1.6.4.1
		priSsidPon OBJECT-TYPE
			SYNTAX INTEGER (1..16)
			MAX-ACCESS read-write
			STATUS current
			DESCRIPTION
				"Description."
			::= { gOnuPriWifiSsid 1 }

		
--  1.3.6.1.4.1.37950.1.1.6.1.6.4.2
		-- 1.3.6.1.4.1.37950.1.1.6.1.6.4.2
		proSsidOnu OBJECT-TYPE
			SYNTAX INTEGER (1..65535)
			MAX-ACCESS read-write
			STATUS current
			DESCRIPTION
				"Description."
			::= { gOnuPriWifiSsid 2 }

		
--  1.3.6.1.4.1.37950.1.1.6.1.6.4.3
		-- 1.3.6.1.4.1.37950.1.1.6.1.6.4.3
		priSsidId OBJECT-TYPE
			SYNTAX INTEGER (1..10)
			MAX-ACCESS read-write
			STATUS current
			DESCRIPTION
				"Description."
			::= { gOnuPriWifiSsid 3 }

		
--  1.3.6.1.4.1.37950.1.1.6.1.6.4.4
		-- 1.3.6.1.4.1.37950.1.1.6.1.6.4.4
		priSsidName OBJECT-TYPE
			SYNTAX OCTET STRING
			MAX-ACCESS read-write
			STATUS current
			DESCRIPTION
				"Description."
			::= { gOnuPriWifiSsid 4 }

		
--  1.3.6.1.4.1.37950.1.1.6.1.6.4.5
		-- 1.3.6.1.4.1.37950.1.1.6.1.6.4.5
		priSsidEnable OBJECT-TYPE
			SYNTAX INTEGER
				{
				disable(0),
				enable(1)
				}
			MAX-ACCESS read-write
			STATUS current
			DESCRIPTION
				"Description."
			::= { gOnuPriWifiSsid 5 }

		
--  1.3.6.1.4.1.37950.1.1.6.1.6.4.6
		-- 1.3.6.1.4.1.37950.1.1.6.1.6.4.6
		priSsidHide OBJECT-TYPE
			SYNTAX INTEGER
				{
				disable(0),
				enable(1)
				}
			MAX-ACCESS read-write
			STATUS current
			DESCRIPTION
				"Description."
			::= { gOnuPriWifiSsid 6 }

		
--  1.3.6.1.4.1.37950.1.1.6.1.6.4.7
		-- 1.3.6.1.4.1.37950.1.1.6.1.6.4.7
		priSsidAuthMode OBJECT-TYPE
			SYNTAX INTEGER
				{
				open(1),
				shared(2),
				wepauto(3),
				wpapsk(4),
				wpa(5),
				wpa2psk(6),
				wpa2(7),
				wpa_wpa2(8),
				wpapsk_wpa2psk(9),
				wpa3psk(10),
				wpa2psk_wpa3psk(11)
				}
			MAX-ACCESS read-write
			STATUS current
			DESCRIPTION
				"Description."
			::= { gOnuPriWifiSsid 7 }

		
--  1.3.6.1.4.1.37950.1.1.6.1.6.4.8
		-- 1.3.6.1.4.1.37950.1.1.6.1.6.4.8
		priSsidEncrypTpye OBJECT-TYPE
			SYNTAX INTEGER
				{
				none(1),
				wep(2),
				tkip(3),
				aes(4),
				tkipaes(5)
				}
			MAX-ACCESS read-write
			STATUS current
			DESCRIPTION
				"Description."
			::= { gOnuPriWifiSsid 8 }

		
--  1.3.6.1.4.1.37950.1.1.6.1.6.4.9
		-- 1.3.6.1.4.1.37950.1.1.6.1.6.4.9
		priSsidPresharedKey OBJECT-TYPE
			SYNTAX OCTET STRING
			MAX-ACCESS read-write
			STATUS current
			DESCRIPTION
				"Description."
			::= { gOnuPriWifiSsid 9 }

		
--  1.3.6.1.4.1.37950.1.1.6.1.6.4.10
		-- 1.3.6.1.4.1.37950.1.1.6.1.6.4.10
		priSsidPrekeyInterval OBJECT-TYPE
			SYNTAX INTEGER (0..4194303)
			MAX-ACCESS read-write
			STATUS current
			DESCRIPTION
				"Description."
			::= { gOnuPriWifiSsid 10 }

		
--  1.3.6.1.4.1.37950.1.1.6.1.6.4.11
		-- 1.3.6.1.4.1.37950.1.1.6.1.6.4.11
		priSsidRadiusSeripType OBJECT-TYPE
			SYNTAX INTEGER
				{
				ipv4(1),
				ipv6(2),
				ipv4z(3),
				ipv6z(4),
				dns(16)
				}
			MAX-ACCESS read-write
			STATUS current
			DESCRIPTION
				"Description."
			::= { gOnuPriWifiSsid 11 }

		
--  1.3.6.1.4.1.37950.1.1.6.1.6.4.12
		-- 1.3.6.1.4.1.37950.1.1.6.1.6.4.12
		priSsidRadiusSerip OBJECT-TYPE
			SYNTAX OCTET STRING
			MAX-ACCESS read-write
			STATUS current
			DESCRIPTION
				"Description."
			::= { gOnuPriWifiSsid 12 }

		
--  1.3.6.1.4.1.37950.1.1.6.1.6.4.13
		-- 1.3.6.1.4.1.37950.1.1.6.1.6.4.13
		priSsidRadiusServipPrefixLen OBJECT-TYPE
			SYNTAX INTEGER (0..255)
			MAX-ACCESS read-write
			STATUS current
			DESCRIPTION
				"Description."
			::= { gOnuPriWifiSsid 13 }

		
--  1.3.6.1.4.1.37950.1.1.6.1.6.4.14
		-- 1.3.6.1.4.1.37950.1.1.6.1.6.4.14
		priSsidRadiusPort OBJECT-TYPE
			SYNTAX INTEGER (0..65535)
			MAX-ACCESS read-write
			STATUS current
			DESCRIPTION
				"Description."
			::= { gOnuPriWifiSsid 14 }

		
--  1.3.6.1.4.1.37950.1.1.6.1.6.4.15
		-- 1.3.6.1.4.1.37950.1.1.6.1.6.4.15
		priSsidRadiusKey OBJECT-TYPE
			SYNTAX OCTET STRING
			MAX-ACCESS read-write
			STATUS current
			DESCRIPTION
				"Description."
			::= { gOnuPriWifiSsid 15 }

		
--  1.3.6.1.4.1.37950.1.1.6.1.6.4.16
		-- 1.3.6.1.4.1.37950.1.1.6.1.6.4.16
		priSsidWepEncrytionLevel OBJECT-TYPE
			SYNTAX INTEGER
				{
				s64bit(1),
				s128bit(2)
				}
			MAX-ACCESS read-write
			STATUS current
			DESCRIPTION
				"Description."
			::= { gOnuPriWifiSsid 16 }

		
--  1.3.6.1.4.1.37950.1.1.6.1.6.4.17
		-- 1.3.6.1.4.1.37950.1.1.6.1.6.4.17
		priSsidWepKeyIndex OBJECT-TYPE
			SYNTAX INTEGER (1..4)
			MAX-ACCESS read-write
			STATUS current
			DESCRIPTION
				"Description."
			::= { gOnuPriWifiSsid 17 }

		
--  1.3.6.1.4.1.37950.1.1.6.1.6.4.18
		-- 1.3.6.1.4.1.37950.1.1.6.1.6.4.18
		priSsidWepKey1 OBJECT-TYPE
			SYNTAX OCTET STRING
			MAX-ACCESS read-write
			STATUS current
			DESCRIPTION
				"Description."
			::= { gOnuPriWifiSsid 18 }

		
--  1.3.6.1.4.1.37950.1.1.6.1.6.4.19
		-- 1.3.6.1.4.1.37950.1.1.6.1.6.4.19
		priSsidWepKey2 OBJECT-TYPE
			SYNTAX OCTET STRING
			MAX-ACCESS read-write
			STATUS current
			DESCRIPTION
				"Description."
			::= { gOnuPriWifiSsid 19 }

		
--  1.3.6.1.4.1.37950.1.1.6.1.6.4.20
		-- 1.3.6.1.4.1.37950.1.1.6.1.6.4.20
		priSsidWepKey3 OBJECT-TYPE
			SYNTAX OCTET STRING
			MAX-ACCESS read-write
			STATUS current
			DESCRIPTION
				"Description."
			::= { gOnuPriWifiSsid 20 }

		
--  1.3.6.1.4.1.37950.1.1.6.1.6.4.21
		-- 1.3.6.1.4.1.37950.1.1.6.1.6.4.21
		priSsidWepKey4 OBJECT-TYPE
			SYNTAX OCTET STRING
			MAX-ACCESS read-write
			STATUS current
			DESCRIPTION
				"Description."
			::= { gOnuPriWifiSsid 21 }

		
--  1.3.6.1.4.1.37950.1.1.6.1.6.4.22
		-- 1.3.6.1.4.1.37950.1.1.6.1.6.4.22
		priSsidAction OBJECT-TYPE
			SYNTAX INTEGER
				{
				commit(1),
				remove(2)
				}
			MAX-ACCESS read-write
			STATUS current
			DESCRIPTION
				"Description."
			::= { gOnuPriWifiSsid 22 }

		
--  1.3.6.1.4.1.37950.1.1.6.1.6.5
		-- 1.3.6.1.4.1.37950.1.1.6.1.6.5
		gOnuPriVoip OBJECT IDENTIFIER ::= { gOnuPriCfg 5 }

		
--  1.3.6.1.4.1.37950.1.1.6.1.6.5.1
		-- 1.3.6.1.4.1.37950.1.1.6.1.6.5.1
		gOnuPriVoipPonInx OBJECT-TYPE
			SYNTAX Integer32 (1..16)
			MAX-ACCESS read-write
			STATUS current
			DESCRIPTION
				"Description."
			::= { gOnuPriVoip 1 }

		
--  1.3.6.1.4.1.37950.1.1.6.1.6.5.2
		-- 1.3.6.1.4.1.37950.1.1.6.1.6.5.2
		gOnuPriVoipOnuInx OBJECT-TYPE
			SYNTAX Integer32 (1..128)
			MAX-ACCESS read-write
			STATUS current
			DESCRIPTION
				"Description."
			::= { gOnuPriVoip 2 }

		
--  1.3.6.1.4.1.37950.1.1.6.1.6.5.3
		-- 1.3.6.1.4.1.37950.1.1.6.1.6.5.3
		gOnuPriVoipAction OBJECT-TYPE
			SYNTAX INTEGER
				{
				reregister(1),
				deregister(2),
				reset(3)
				}
			MAX-ACCESS read-write
			STATUS current
			DESCRIPTION
				"Description."
			::= { gOnuPriVoip 3 }

		
--  1.3.6.1.4.1.37950.1.1.6.1.6.6
		-- 1.3.6.1.4.1.37950.1.1.6.1.6.6
		gOnuPriSipParam OBJECT IDENTIFIER ::= { gOnuPriCfg 6 }

		
--  1.3.6.1.4.1.37950.1.1.6.1.6.6.1
		-- 1.3.6.1.4.1.37950.1.1.6.1.6.6.1
		priSipParamPon OBJECT-TYPE
			SYNTAX Integer32 (1..16)
			MAX-ACCESS read-write
			STATUS current
			DESCRIPTION
				"Description."
			::= { gOnuPriSipParam 1 }

		
--  1.3.6.1.4.1.37950.1.1.6.1.6.6.2
		-- 1.3.6.1.4.1.37950.1.1.6.1.6.6.2
		priSipParamOnu OBJECT-TYPE
			SYNTAX Integer32 (1..65535)
			MAX-ACCESS read-write
			STATUS current
			DESCRIPTION
				"Description."
			::= { gOnuPriSipParam 2 }

		
--  1.3.6.1.4.1.37950.1.1.6.1.6.6.3
		-- 1.3.6.1.4.1.37950.1.1.6.1.6.6.3
		priProxyServIp OBJECT-TYPE
			SYNTAX OCTET STRING
			MAX-ACCESS read-write
			STATUS current
			DESCRIPTION
				"Description."
			::= { gOnuPriSipParam 3 }

		
--  1.3.6.1.4.1.37950.1.1.6.1.6.6.4
		-- 1.3.6.1.4.1.37950.1.1.6.1.6.6.4
		priProxyServPort OBJECT-TYPE
			SYNTAX Integer32 (0..65535)
			MAX-ACCESS read-write
			STATUS current
			DESCRIPTION
				"Description."
			::= { gOnuPriSipParam 4 }

		
--  1.3.6.1.4.1.37950.1.1.6.1.6.6.5
		-- 1.3.6.1.4.1.37950.1.1.6.1.6.6.5
		priBakProxyServIp OBJECT-TYPE
			SYNTAX OCTET STRING
			MAX-ACCESS read-write
			STATUS current
			DESCRIPTION
				"Description."
			::= { gOnuPriSipParam 5 }

		
--  1.3.6.1.4.1.37950.1.1.6.1.6.6.6
		-- 1.3.6.1.4.1.37950.1.1.6.1.6.6.6
		priBakProxyServPort OBJECT-TYPE
			SYNTAX Integer32 (0..65535)
			MAX-ACCESS read-write
			STATUS current
			DESCRIPTION
				"Description."
			::= { gOnuPriSipParam 6 }

		
--  1.3.6.1.4.1.37950.1.1.6.1.6.6.7
		-- 1.3.6.1.4.1.37950.1.1.6.1.6.6.7
		priRegServIp OBJECT-TYPE
			SYNTAX OCTET STRING
			MAX-ACCESS read-write
			STATUS current
			DESCRIPTION
				"Description."
			::= { gOnuPriSipParam 7 }

		
--  1.3.6.1.4.1.37950.1.1.6.1.6.6.8
		-- 1.3.6.1.4.1.37950.1.1.6.1.6.6.8
		priRegServPort OBJECT-TYPE
			SYNTAX Integer32 (0..65535)
			MAX-ACCESS read-write
			STATUS current
			DESCRIPTION
				"Description."
			::= { gOnuPriSipParam 8 }

		
--  1.3.6.1.4.1.37950.1.1.6.1.6.6.9
		-- 1.3.6.1.4.1.37950.1.1.6.1.6.6.9
		priBakRegServIp OBJECT-TYPE
			SYNTAX OCTET STRING
			MAX-ACCESS read-write
			STATUS current
			DESCRIPTION
				"Description."
			::= { gOnuPriSipParam 9 }

		
--  1.3.6.1.4.1.37950.1.1.6.1.6.6.10
		-- 1.3.6.1.4.1.37950.1.1.6.1.6.6.10
		priBakRegServPort OBJECT-TYPE
			SYNTAX Integer32 (0..65535)
			MAX-ACCESS read-write
			STATUS current
			DESCRIPTION
				"Description."
			::= { gOnuPriSipParam 10 }

		
--  1.3.6.1.4.1.37950.1.1.6.1.6.6.11
		-- 1.3.6.1.4.1.37950.1.1.6.1.6.6.11
		priOutBndServIp OBJECT-TYPE
			SYNTAX OCTET STRING
			MAX-ACCESS read-write
			STATUS current
			DESCRIPTION
				"Description."
			::= { gOnuPriSipParam 11 }

		
--  1.3.6.1.4.1.37950.1.1.6.1.6.6.12
		-- 1.3.6.1.4.1.37950.1.1.6.1.6.6.12
		priOutBndServPort OBJECT-TYPE
			SYNTAX Integer32 (0..65535)
			MAX-ACCESS read-write
			STATUS current
			DESCRIPTION
				"Description."
			::= { gOnuPriSipParam 12 }

		
--  1.3.6.1.4.1.37950.1.1.6.1.6.6.13
		-- 1.3.6.1.4.1.37950.1.1.6.1.6.6.13
		priSipParamMgPort OBJECT-TYPE
			SYNTAX Integer32 (0..65535)
			MAX-ACCESS read-write
			STATUS current
			DESCRIPTION
				"Description."
			::= { gOnuPriSipParam 13 }

		
--  1.3.6.1.4.1.37950.1.1.6.1.6.6.14
		-- 1.3.6.1.4.1.37950.1.1.6.1.6.6.14
		priRegInterval OBJECT-TYPE
			SYNTAX Integer32 (0..10000000)
			MAX-ACCESS read-write
			STATUS current
			DESCRIPTION
				"Description."
			::= { gOnuPriSipParam 14 }

		
--  1.3.6.1.4.1.37950.1.1.6.1.6.6.15
		-- 1.3.6.1.4.1.37950.1.1.6.1.6.6.15
		priSipGloParamAction OBJECT-TYPE
			SYNTAX INTEGER { commit(1) }
			MAX-ACCESS read-write
			STATUS current
			DESCRIPTION
				"Description."
			::= { gOnuPriSipParam 15 }

		
--  1.3.6.1.4.1.37950.1.1.6.1.6.7
		-- 1.3.6.1.4.1.37950.1.1.6.1.6.7
		gOnuPriSipDigitMap OBJECT IDENTIFIER ::= { gOnuPriCfg 7 }

		
--  1.3.6.1.4.1.37950.1.1.6.1.6.7.1
		-- 1.3.6.1.4.1.37950.1.1.6.1.6.7.1
		priSipDigitMapPon OBJECT-TYPE
			SYNTAX Integer32 (1..16)
			MAX-ACCESS read-write
			STATUS current
			DESCRIPTION
				"Description."
			::= { gOnuPriSipDigitMap 1 }

		
--  1.3.6.1.4.1.37950.1.1.6.1.6.7.2
		-- 1.3.6.1.4.1.37950.1.1.6.1.6.7.2
		priSipDigitMapOnu OBJECT-TYPE
			SYNTAX Integer32 (1..65535)
			MAX-ACCESS read-write
			STATUS current
			DESCRIPTION
				"Description."
			::= { gOnuPriSipDigitMap 2 }

		
--  1.3.6.1.4.1.37950.1.1.6.1.6.7.3
		-- 1.3.6.1.4.1.37950.1.1.6.1.6.7.3
		priSipDigitMapBlock OBJECT-TYPE
			SYNTAX OCTET STRING
			MAX-ACCESS read-write
			STATUS current
			DESCRIPTION
				"Description."
			::= { gOnuPriSipDigitMap 3 }

		
--  1.3.6.1.4.1.37950.1.1.6.1.6.7.4
		-- 1.3.6.1.4.1.37950.1.1.6.1.6.7.4
		priSipDigitMapAction OBJECT-TYPE
			SYNTAX INTEGER { commit(1) }
			MAX-ACCESS read-write
			STATUS current
			DESCRIPTION
				"Description."
			::= { gOnuPriSipDigitMap 4 }

		
--  1.3.6.1.4.1.37950.1.1.6.1.6.8
		-- 1.3.6.1.4.1.37950.1.1.6.1.6.8
		gOnuPriSipUserParam OBJECT IDENTIFIER ::= { gOnuPriCfg 8 }

		
--  1.3.6.1.4.1.37950.1.1.6.1.6.8.1
		-- 1.3.6.1.4.1.37950.1.1.6.1.6.8.1
		sipUserPonNo OBJECT-TYPE
			SYNTAX Integer32 (1..16)
			MAX-ACCESS read-write
			STATUS current
			DESCRIPTION
				"Description."
			::= { gOnuPriSipUserParam 1 }

		
--  1.3.6.1.4.1.37950.1.1.6.1.6.8.2
		-- 1.3.6.1.4.1.37950.1.1.6.1.6.8.2
		sipUserOnuNo OBJECT-TYPE
			SYNTAX Integer32 (1..65535)
			MAX-ACCESS read-write
			STATUS current
			DESCRIPTION
				"Description."
			::= { gOnuPriSipUserParam 2 }

		
--  1.3.6.1.4.1.37950.1.1.6.1.6.8.3
		-- 1.3.6.1.4.1.37950.1.1.6.1.6.8.3
		sipUserPotsNo OBJECT-TYPE
			SYNTAX Integer32 (1..255)
			MAX-ACCESS read-write
			STATUS current
			DESCRIPTION
				"Description."
			::= { gOnuPriSipUserParam 3 }

		
--  1.3.6.1.4.1.37950.1.1.6.1.6.8.4
		-- 1.3.6.1.4.1.37950.1.1.6.1.6.8.4
		sipUserAccountAcitve OBJECT-TYPE
			SYNTAX INTEGER
				{
				disable(0),
				enable(1)
				}
			MAX-ACCESS read-write
			STATUS current
			DESCRIPTION
				"Description."
			::= { gOnuPriSipUserParam 4 }

		
--  1.3.6.1.4.1.37950.1.1.6.1.6.8.5
		-- 1.3.6.1.4.1.37950.1.1.6.1.6.8.5
		sipUserAccount OBJECT-TYPE
			SYNTAX OCTET STRING
			MAX-ACCESS read-write
			STATUS current
			DESCRIPTION
				"Description."
			::= { gOnuPriSipUserParam 5 }

		
--  1.3.6.1.4.1.37950.1.1.6.1.6.8.6
		-- 1.3.6.1.4.1.37950.1.1.6.1.6.8.6
		sipUserName OBJECT-TYPE
			SYNTAX OCTET STRING
			MAX-ACCESS read-write
			STATUS current
			DESCRIPTION
				"Description."
			::= { gOnuPriSipUserParam 6 }

		
--  1.3.6.1.4.1.37950.1.1.6.1.6.8.7
		-- 1.3.6.1.4.1.37950.1.1.6.1.6.8.7
		sipUserPw OBJECT-TYPE
			SYNTAX OCTET STRING
			MAX-ACCESS read-write
			STATUS current
			DESCRIPTION
				"Description."
			::= { gOnuPriSipUserParam 7 }

		
--  1.3.6.1.4.1.37950.1.1.6.1.6.8.8
		-- 1.3.6.1.4.1.37950.1.1.6.1.6.8.8
		sipUserAction OBJECT-TYPE
			SYNTAX INTEGER { commit(1) }
			MAX-ACCESS read-write
			STATUS current
			DESCRIPTION
				"Description."
			::= { gOnuPriSipUserParam 8 }

		
--  1.3.6.1.4.1.37950.1.1.6.1.6.9
		-- 1.3.6.1.4.1.37950.1.1.6.1.6.9
		gOnuPriPotsParam OBJECT IDENTIFIER ::= { gOnuPriCfg 9 }

		
--  1.3.6.1.4.1.37950.1.1.6.1.6.9.1
		-- 1.3.6.1.4.1.37950.1.1.6.1.6.9.1
		priPotsParameterPon OBJECT-TYPE
			SYNTAX Integer32 (1..16)
			MAX-ACCESS read-write
			STATUS current
			DESCRIPTION
				"Description."
			::= { gOnuPriPotsParam 1 }

		
--  1.3.6.1.4.1.37950.1.1.6.1.6.9.2
		-- 1.3.6.1.4.1.37950.1.1.6.1.6.9.2
		priPotsParameterOnu OBJECT-TYPE
			SYNTAX Integer32 (1..65535)
			MAX-ACCESS read-write
			STATUS current
			DESCRIPTION
				"Description."
			::= { gOnuPriPotsParam 2 }

		
--  1.3.6.1.4.1.37950.1.1.6.1.6.9.3
		-- 1.3.6.1.4.1.37950.1.1.6.1.6.9.3
		priPotsParameterPotsNo OBJECT-TYPE
			SYNTAX Integer32 (1..255)
			MAX-ACCESS read-write
			STATUS current
			DESCRIPTION
				"Description."
			::= { gOnuPriPotsParam 3 }

		
--  1.3.6.1.4.1.37950.1.1.6.1.6.9.4
		-- 1.3.6.1.4.1.37950.1.1.6.1.6.9.4
		priPotsParameterVar OBJECT-TYPE
			SYNTAX INTEGER
				{
				disable(0),
				enable(1)
				}
			MAX-ACCESS read-write
			STATUS current
			DESCRIPTION
				"Description."
			::= { gOnuPriPotsParam 4 }

		
--  1.3.6.1.4.1.37950.1.1.6.1.6.9.5
		-- 1.3.6.1.4.1.37950.1.1.6.1.6.9.5
		priPotsParameterEchoCancle OBJECT-TYPE
			SYNTAX INTEGER
				{
				disable(0),
				enable(1)
				}
			MAX-ACCESS read-write
			STATUS current
			DESCRIPTION
				"Description."
			::= { gOnuPriPotsParam 5 }

		
--  1.3.6.1.4.1.37950.1.1.6.1.6.9.6
		-- 1.3.6.1.4.1.37950.1.1.6.1.6.9.6
		priPotsPtInutGain OBJECT-TYPE
			SYNTAX Integer32 (-32..32)
			MAX-ACCESS read-write
			STATUS current
			DESCRIPTION
				"Description."
			::= { gOnuPriPotsParam 6 }

		
--  1.3.6.1.4.1.37950.1.1.6.1.6.9.7
		-- 1.3.6.1.4.1.37950.1.1.6.1.6.9.7
		priPotsPtOutputGain OBJECT-TYPE
			SYNTAX Integer32 (-32..32)
			MAX-ACCESS read-write
			STATUS current
			DESCRIPTION
				"Description."
			::= { gOnuPriPotsParam 7 }

		
--  1.3.6.1.4.1.37950.1.1.6.1.6.9.8
		-- 1.3.6.1.4.1.37950.1.1.6.1.6.9.8
		priPotsPtDtmfMode OBJECT-TYPE
			SYNTAX INTEGER
				{
				transparent(0),
				rfc2833(1),
				rfc2833_redundancyl(2),
				outband(3)
				}
			MAX-ACCESS read-write
			STATUS current
			DESCRIPTION
				"Description."
			::= { gOnuPriPotsParam 8 }

		
--  1.3.6.1.4.1.37950.1.1.6.1.6.9.9
		-- 1.3.6.1.4.1.37950.1.1.6.1.6.9.9
		priPotsPtAction OBJECT-TYPE
			SYNTAX INTEGER
				{
				commit(1),
				remove(2)
				}
			MAX-ACCESS read-write
			STATUS current
			DESCRIPTION
				"Description."
			::= { gOnuPriPotsParam 9 }

		
--  1.3.6.1.4.1.37950.1.1.6.1.6.10
		-- 1.3.6.1.4.1.37950.1.1.6.1.6.10
		gOnuPriLanBindMode OBJECT IDENTIFIER ::= { gOnuPriCfg 10 }

		
--  1.3.6.1.4.1.37950.1.1.6.1.6.10.1
		-- 1.3.6.1.4.1.37950.1.1.6.1.6.10.1
		priLanBindModePon OBJECT-TYPE
			SYNTAX Integer32 (1..16)
			MAX-ACCESS read-write
			STATUS current
			DESCRIPTION
				"Description."
			::= { gOnuPriLanBindMode 1 }

		
--  1.3.6.1.4.1.37950.1.1.6.1.6.10.2
		-- 1.3.6.1.4.1.37950.1.1.6.1.6.10.2
		priLanBindModeOnu OBJECT-TYPE
			SYNTAX Integer32 (1..128)
			MAX-ACCESS read-write
			STATUS current
			DESCRIPTION
				"Description."
			::= { gOnuPriLanBindMode 2 }

		
--  1.3.6.1.4.1.37950.1.1.6.1.6.10.3
		-- 1.3.6.1.4.1.37950.1.1.6.1.6.10.3
		priLanBindModePortId OBJECT-TYPE
			SYNTAX Integer32
			MAX-ACCESS read-write
			STATUS current
			DESCRIPTION
				"Description."
			::= { gOnuPriLanBindMode 3 }

		
--  1.3.6.1.4.1.37950.1.1.6.1.6.10.4
		-- 1.3.6.1.4.1.37950.1.1.6.1.6.10.4
		priLanBindModeBMode OBJECT-TYPE
			SYNTAX INTEGER
				{
				null(0),
				port(1),
				vlan(2)
				}
			MAX-ACCESS read-write
			STATUS current
			DESCRIPTION
				"Description."
			::= { gOnuPriLanBindMode 4 }

		
--  1.3.6.1.4.1.37950.1.1.6.1.6.10.5
		-- 1.3.6.1.4.1.37950.1.1.6.1.6.10.5
		priLanBindModeLanVlan1 OBJECT-TYPE
			SYNTAX Integer32 (0..65536)
			MAX-ACCESS read-write
			STATUS current
			DESCRIPTION
				"Description."
			::= { gOnuPriLanBindMode 5 }

		
--  1.3.6.1.4.1.37950.1.1.6.1.6.10.6
		-- 1.3.6.1.4.1.37950.1.1.6.1.6.10.6
		priLanBindModeWanVlan1 OBJECT-TYPE
			SYNTAX Integer32 (0..65536)
			MAX-ACCESS read-write
			STATUS current
			DESCRIPTION
				"Description."
			::= { gOnuPriLanBindMode 6 }

		
--  1.3.6.1.4.1.37950.1.1.6.1.6.10.7
		-- 1.3.6.1.4.1.37950.1.1.6.1.6.10.7
		priLanBindModeLanVlan2 OBJECT-TYPE
			SYNTAX Integer32 (0..65536)
			MAX-ACCESS read-write
			STATUS current
			DESCRIPTION
				"Description."
			::= { gOnuPriLanBindMode 7 }

		
--  1.3.6.1.4.1.37950.1.1.6.1.6.10.8
		-- 1.3.6.1.4.1.37950.1.1.6.1.6.10.8
		priLanBindModeWanVlan2 OBJECT-TYPE
			SYNTAX Integer32 (0..65536)
			MAX-ACCESS read-write
			STATUS current
			DESCRIPTION
				"Description."
			::= { gOnuPriLanBindMode 8 }

		
--  1.3.6.1.4.1.37950.1.1.6.1.6.10.9
		-- 1.3.6.1.4.1.37950.1.1.6.1.6.10.9
		priLanBindModeLanVlan3 OBJECT-TYPE
			SYNTAX Integer32 (0..65536)
			MAX-ACCESS read-write
			STATUS current
			DESCRIPTION
				"Description."
			::= { gOnuPriLanBindMode 9 }

		
--  1.3.6.1.4.1.37950.1.1.6.1.6.10.10
		-- 1.3.6.1.4.1.37950.1.1.6.1.6.10.10
		priLanBindModeWanVlan3 OBJECT-TYPE
			SYNTAX Integer32 (0..65536)
			MAX-ACCESS read-write
			STATUS current
			DESCRIPTION
				"Description."
			::= { gOnuPriLanBindMode 10 }

		
--  1.3.6.1.4.1.37950.1.1.6.1.6.10.11
		-- 1.3.6.1.4.1.37950.1.1.6.1.6.10.11
		priLanBindModeLanVlan4 OBJECT-TYPE
			SYNTAX Integer32 (0..65536)
			MAX-ACCESS read-write
			STATUS current
			DESCRIPTION
				"Description."
			::= { gOnuPriLanBindMode 11 }

		
--  1.3.6.1.4.1.37950.1.1.6.1.6.10.12
		-- 1.3.6.1.4.1.37950.1.1.6.1.6.10.12
		priLanBindModeWanVlan4 OBJECT-TYPE
			SYNTAX Integer32 (0..65536)
			MAX-ACCESS read-write
			STATUS current
			DESCRIPTION
				"Description."
			::= { gOnuPriLanBindMode 12 }

		
--  1.3.6.1.4.1.37950.1.1.6.1.6.10.13
		-- 1.3.6.1.4.1.37950.1.1.6.1.6.10.13
		priLanBindModeAction OBJECT-TYPE
			SYNTAX INTEGER { commit(1) }
			MAX-ACCESS read-write
			STATUS current
			DESCRIPTION
				"Description."
			::= { gOnuPriLanBindMode 13 }

		
--  1.3.6.1.4.1.37950.1.1.6.1.6.11
		-- 1.3.6.1.4.1.37950.1.1.6.1.6.11
		gOnuPriMiscCtrlOp OBJECT IDENTIFIER ::= { gOnuPriCfg 11 }

		
--  1.3.6.1.4.1.37950.1.1.6.1.6.11.1
		-- 1.3.6.1.4.1.37950.1.1.6.1.6.11.1
		priMiscCtrlOpPon OBJECT-TYPE
			SYNTAX Integer32 (1..16)
			MAX-ACCESS read-write
			STATUS current
			DESCRIPTION
				"Description."
			::= { gOnuPriMiscCtrlOp 1 }

		
--  1.3.6.1.4.1.37950.1.1.6.1.6.11.2
		-- 1.3.6.1.4.1.37950.1.1.6.1.6.11.2
		priMiscCtrlOpOnu OBJECT-TYPE
			SYNTAX Integer32 (1..128)
			MAX-ACCESS read-write
			STATUS current
			DESCRIPTION
				"Description."
			::= { gOnuPriMiscCtrlOp 2 }

		
--  1.3.6.1.4.1.37950.1.1.6.1.6.11.3
		-- 1.3.6.1.4.1.37950.1.1.6.1.6.11.3
		priMiscCtrlOpSaveCfg OBJECT-TYPE
			SYNTAX INTEGER { commit(1) }
			MAX-ACCESS read-write
			STATUS current
			DESCRIPTION
				"Description."
			::= { gOnuPriMiscCtrlOp 3 }

		
--  1.3.6.1.4.1.37950.1.1.6.1.6.11.4
		-- 1.3.6.1.4.1.37950.1.1.6.1.6.11.4
		priMiscCtrlOpRestoreCfg OBJECT-TYPE
			SYNTAX INTEGER { commit(1) }
			MAX-ACCESS read-write
			STATUS current
			DESCRIPTION
				"Description."
			::= { gOnuPriMiscCtrlOp 4 }

		
--  1.3.6.1.4.1.37950.1.1.6.1.6.11.5
		-- 1.3.6.1.4.1.37950.1.1.6.1.6.11.5
		priMiscCtrlOpCatvEnable OBJECT-TYPE
			SYNTAX INTEGER
				{
				disable(0),
				enable(1)
				}
			MAX-ACCESS read-write
			STATUS current
			DESCRIPTION
				"Description."
			::= { gOnuPriMiscCtrlOp 5 }

		
--  1.3.6.1.4.1.37950.1.1.6.1.6.11.6
		-- 1.3.6.1.4.1.37950.1.1.6.1.6.11.6
		priMiscCtrlOpIgmpEnable OBJECT-TYPE
			SYNTAX INTEGER
				{
				disable(0),
				enable(1)
				}
			MAX-ACCESS read-write
			STATUS current
			DESCRIPTION
				"Description."
			::= { gOnuPriMiscCtrlOp 6 }

		
--  1.3.6.1.4.1.37950.1.1.6.1.6.11.7
		-- 1.3.6.1.4.1.37950.1.1.6.1.6.11.7
		priMiscCtrlOpStpEnable OBJECT-TYPE
			SYNTAX INTEGER
				{
				disable(0),
				enable(1)
				}
			MAX-ACCESS read-write
			STATUS current
			DESCRIPTION
				"Description."
			::= { gOnuPriMiscCtrlOp 7 }

		
--  1.3.6.1.4.1.37950.1.1.6.1.6.11.8
		-- 1.3.6.1.4.1.37950.1.1.6.1.6.11.8
		priMiscCtrlOpPortIsoEnable OBJECT-TYPE
			SYNTAX INTEGER
				{
				disable(0),
				enable(1)
				}
			MAX-ACCESS read-write
			STATUS current
			DESCRIPTION
				"Description."
			::= { gOnuPriMiscCtrlOp 8 }

		
--  1.3.6.1.4.1.37950.1.1.6.1.6.11.9
		-- 1.3.6.1.4.1.37950.1.1.6.1.6.11.9
		priMiscCtrlOpResetButton OBJECT-TYPE
			SYNTAX INTEGER
				{
				disable(0),
				enable(1)
				}
			MAX-ACCESS read-write
			STATUS current
			DESCRIPTION
				"Description."
			::= { gOnuPriMiscCtrlOp 9 }

		
--  1.3.6.1.4.1.37950.1.1.6.1.6.12
		-- 1.3.6.1.4.1.37950.1.1.6.1.6.12
		gOnuPriSpeedLimit OBJECT IDENTIFIER ::= { gOnuPriCfg 12 }

		
--  1.3.6.1.4.1.37950.1.1.6.1.6.12.1
		-- 1.3.6.1.4.1.37950.1.1.6.1.6.12.1
		priSpeedLimitPon OBJECT-TYPE
			SYNTAX Integer32 (1..16)
			MAX-ACCESS read-write
			STATUS current
			DESCRIPTION
				"Description."
			::= { gOnuPriSpeedLimit 1 }

		
--  1.3.6.1.4.1.37950.1.1.6.1.6.12.2
		-- 1.3.6.1.4.1.37950.1.1.6.1.6.12.2
		priSpeedLimitOnu OBJECT-TYPE
			SYNTAX Integer32 (1..128)
			MAX-ACCESS read-write
			STATUS current
			DESCRIPTION
				"Description."
			::= { gOnuPriSpeedLimit 2 }

		
--  1.3.6.1.4.1.37950.1.1.6.1.6.12.3
		-- 1.3.6.1.4.1.37950.1.1.6.1.6.12.3
		priSpeedLimitUpsLimit OBJECT-TYPE
			SYNTAX Integer32
			MAX-ACCESS read-write
			STATUS current
			DESCRIPTION
				"Description."
			::= { gOnuPriSpeedLimit 3 }

		
--  1.3.6.1.4.1.37950.1.1.6.1.6.12.4
		-- 1.3.6.1.4.1.37950.1.1.6.1.6.12.4
		priSpeedLimitDssLimit OBJECT-TYPE
			SYNTAX Integer32
			MAX-ACCESS read-write
			STATUS current
			DESCRIPTION
				"Description."
			::= { gOnuPriSpeedLimit 4 }

		
--  1.3.6.1.4.1.37950.1.1.6.1.6.12.5
		-- 1.3.6.1.4.1.37950.1.1.6.1.6.12.5
		priSpeedLimitAction OBJECT-TYPE
			SYNTAX INTEGER { commit(1) }
			MAX-ACCESS read-write
			STATUS current
			DESCRIPTION
				"Description."
			::= { gOnuPriSpeedLimit 5 }

		
--  1.3.6.1.4.1.37950.1.1.6.1.6.13
		-- 1.3.6.1.4.1.37950.1.1.6.1.6.13
		gOnuPriMacTableCfg OBJECT IDENTIFIER ::= { gOnuPriCfg 13 }

		
--  1.3.6.1.4.1.37950.1.1.6.1.6.13.1
		-- 1.3.6.1.4.1.37950.1.1.6.1.6.13.1
		priMacTablePon OBJECT-TYPE
			SYNTAX Integer32 (1..16)
			MAX-ACCESS read-write
			STATUS current
			DESCRIPTION
				"Description."
			::= { gOnuPriMacTableCfg 1 }

		
--  1.3.6.1.4.1.37950.1.1.6.1.6.13.2
		-- 1.3.6.1.4.1.37950.1.1.6.1.6.13.2
		priMacTableOnu OBJECT-TYPE
			SYNTAX Integer32 (1..128)
			MAX-ACCESS read-write
			STATUS current
			DESCRIPTION
				"Description."
			::= { gOnuPriMacTableCfg 2 }

		
--  1.3.6.1.4.1.37950.1.1.6.1.6.13.3
		-- 1.3.6.1.4.1.37950.1.1.6.1.6.13.3
		priMacTableMacAgingTime OBJECT-TYPE
			SYNTAX Integer32
			MAX-ACCESS read-write
			STATUS current
			DESCRIPTION
				"Description."
			::= { gOnuPriMacTableCfg 3 }

		
--  1.3.6.1.4.1.37950.1.1.6.1.6.13.4
		-- 1.3.6.1.4.1.37950.1.1.6.1.6.13.4
		priMacTablePonMacLimit OBJECT-TYPE
			SYNTAX Integer32
			MAX-ACCESS read-write
			STATUS current
			DESCRIPTION
				"Description."
			::= { gOnuPriMacTableCfg 4 }

		
--  1.3.6.1.4.1.37950.1.1.6.1.6.13.5
		-- 1.3.6.1.4.1.37950.1.1.6.1.6.13.5
		priMacTableLanMacLimitS OBJECT-TYPE
			SYNTAX Integer32
			MAX-ACCESS read-write
			STATUS current
			DESCRIPTION
				"Description."
			::= { gOnuPriMacTableCfg 5 }

		
--  1.3.6.1.4.1.37950.1.1.6.1.6.13.6
		-- 1.3.6.1.4.1.37950.1.1.6.1.6.13.6
		priMacTableAction OBJECT-TYPE
			SYNTAX INTEGER { commit(1) }
			MAX-ACCESS read-write
			STATUS current
			DESCRIPTION
				"Description."
			::= { gOnuPriMacTableCfg 6 }

		
--  1.3.6.1.4.1.37950.1.1.6.1.6.14
		-- 1.3.6.1.4.1.37950.1.1.6.1.6.14
		gOnuPriMacAddrClean OBJECT IDENTIFIER ::= { gOnuPriCfg 14 }

		
--  1.3.6.1.4.1.37950.1.1.6.1.6.14.1
		-- 1.3.6.1.4.1.37950.1.1.6.1.6.14.1
		priMacAddrCleanPon OBJECT-TYPE
			SYNTAX Integer32 (1..16)
			MAX-ACCESS read-write
			STATUS current
			DESCRIPTION
				"Description."
			::= { gOnuPriMacAddrClean 1 }

		
--  1.3.6.1.4.1.37950.1.1.6.1.6.14.2
		-- 1.3.6.1.4.1.37950.1.1.6.1.6.14.2
		priMacAddrCleanOnu OBJECT-TYPE
			SYNTAX Integer32 (1..128)
			MAX-ACCESS read-write
			STATUS current
			DESCRIPTION
				"Description."
			::= { gOnuPriMacAddrClean 2 }

		
--  1.3.6.1.4.1.37950.1.1.6.1.6.14.3
		-- 1.3.6.1.4.1.37950.1.1.6.1.6.14.3
		priMacAddrCleanAction OBJECT-TYPE
			SYNTAX INTEGER { clean(1) }
			MAX-ACCESS read-write
			STATUS current
			DESCRIPTION
				"Description."
			::= { gOnuPriMacAddrClean 3 }

		
--  1.3.6.1.4.1.37950.1.1.6.1.6.15
		-- 1.3.6.1.4.1.37950.1.1.6.1.6.15
		gOnuPriSecurity OBJECT IDENTIFIER ::= { gOnuPriCfg 15 }

		
--  1.3.6.1.4.1.37950.1.1.6.1.6.15.1
		-- 1.3.6.1.4.1.37950.1.1.6.1.6.15.1
		priPonID OBJECT-TYPE
			SYNTAX Unsigned32
			MAX-ACCESS read-write
			STATUS deprecated
			DESCRIPTION
				"Description."
			::= { gOnuPriSecurity 1 }

		
--  1.3.6.1.4.1.37950.1.1.6.1.6.15.2
		-- 1.3.6.1.4.1.37950.1.1.6.1.6.15.2
		priOnuID OBJECT-TYPE
			SYNTAX Unsigned32
			MAX-ACCESS read-write
			STATUS current
			DESCRIPTION
				"Description."
			::= { gOnuPriSecurity 2 }

		
--  1.3.6.1.4.1.37950.1.1.6.1.6.15.3
		-- 1.3.6.1.4.1.37950.1.1.6.1.6.15.3
		gonuPriUsername OBJECT IDENTIFIER ::= { gOnuPriSecurity 3 }

		
--  1.3.6.1.4.1.37950.1.1.6.1.6.15.3.1
		-- 1.3.6.1.4.1.37950.1.1.6.1.6.15.3.1
		priAdminCtl OBJECT-TYPE
			SYNTAX INTEGER
				{
				disable(0),
				enable(1)
				}
			MAX-ACCESS read-write
			STATUS current
			DESCRIPTION
				"Description."
			::= { gonuPriUsername 1 }

		
--  1.3.6.1.4.1.37950.1.1.6.1.6.15.3.2
		-- 1.3.6.1.4.1.37950.1.1.6.1.6.15.3.2
		priAdminName OBJECT-TYPE
			SYNTAX OCTET STRING
			MAX-ACCESS read-write
			STATUS current
			DESCRIPTION
				"Description."
			::= { gonuPriUsername 2 }

		
--  1.3.6.1.4.1.37950.1.1.6.1.6.15.3.3
		-- 1.3.6.1.4.1.37950.1.1.6.1.6.15.3.3
		priAdminPwd OBJECT-TYPE
			SYNTAX OCTET STRING
			MAX-ACCESS read-write
			STATUS current
			DESCRIPTION
				"Description."
			::= { gonuPriUsername 3 }

		
--  1.3.6.1.4.1.37950.1.1.6.1.6.15.3.4
		-- 1.3.6.1.4.1.37950.1.1.6.1.6.15.3.4
		priUserCtl OBJECT-TYPE
			SYNTAX INTEGER
				{
				disable(0),
				enable(1)
				}
			MAX-ACCESS read-write
			STATUS current
			DESCRIPTION
				"Description."
			::= { gonuPriUsername 4 }

		
--  1.3.6.1.4.1.37950.1.1.6.1.6.15.3.5
		-- 1.3.6.1.4.1.37950.1.1.6.1.6.15.3.5
		priUserName OBJECT-TYPE
			SYNTAX OCTET STRING
			MAX-ACCESS read-write
			STATUS current
			DESCRIPTION
				"Description."
			::= { gonuPriUsername 5 }

		
--  1.3.6.1.4.1.37950.1.1.6.1.6.15.3.6
		-- 1.3.6.1.4.1.37950.1.1.6.1.6.15.3.6
		priUserPwd OBJECT-TYPE
			SYNTAX OCTET STRING
			MAX-ACCESS read-write
			STATUS current
			DESCRIPTION
				"Description."
			::= { gonuPriUsername 6 }

		
--  1.3.6.1.4.1.37950.1.1.6.1.6.15.3.7
		-- 1.3.6.1.4.1.37950.1.1.6.1.6.15.3.7
		priUsernameAction OBJECT-TYPE
			SYNTAX INTEGER { add(1) }
			MAX-ACCESS read-write
			STATUS deprecated
			DESCRIPTION
				"Description."
			::= { gonuPriUsername 7 }

		
--  1.3.6.1.4.1.37950.1.1.6.1.6.15.4
		-- 1.3.6.1.4.1.37950.1.1.6.1.6.15.4
		gonuPriFirewall OBJECT IDENTIFIER ::= { gOnuPriSecurity 4 }

		
--  1.3.6.1.4.1.37950.1.1.6.1.6.15.4.1
		-- 1.3.6.1.4.1.37950.1.1.6.1.6.15.4.1
		priFirewall OBJECT-TYPE
			SYNTAX INTEGER
				{
				disable(0),
				low(1),
				middle(2),
				high(3)
				}
			MAX-ACCESS read-write
			STATUS current
			DESCRIPTION
				"Description."
			::= { gonuPriFirewall 1 }

		
--  1.3.6.1.4.1.37950.1.1.6.1.6.15.5
		-- 1.3.6.1.4.1.37950.1.1.6.1.6.15.5
		gonuPriAcl OBJECT IDENTIFIER ::= { gOnuPriSecurity 5 }

		
--  1.3.6.1.4.1.37950.1.1.6.1.6.15.5.1
		-- 1.3.6.1.4.1.37950.1.1.6.1.6.15.5.1
		priAclProtocol OBJECT-TYPE
			SYNTAX INTEGER
				{
				ping(0),
				telnet(1),
				ftp(2),
				http(3),
				https(4),
				tftp(5),
				ssh(6)
				}
			MAX-ACCESS read-write
			STATUS current
			DESCRIPTION
				"Description."
			::= { gonuPriAcl 1 }

		
--  1.3.6.1.4.1.37950.1.1.6.1.6.15.5.2
		-- 1.3.6.1.4.1.37950.1.1.6.1.6.15.5.2
		priAclCtl OBJECT-TYPE
			SYNTAX INTEGER
				{
				disable(0),
				enable(1)
				}
			MAX-ACCESS read-write
			STATUS current
			DESCRIPTION
				"Description."
			::= { gonuPriAcl 2 }

		
--  1.3.6.1.4.1.37950.1.1.6.1.6.15.5.3
		-- 1.3.6.1.4.1.37950.1.1.6.1.6.15.5.3
		priAclLanCtl OBJECT-TYPE
			SYNTAX INTEGER
				{
				disable(0),
				enable(1)
				}
			MAX-ACCESS read-write
			STATUS current
			DESCRIPTION
				"Description."
			::= { gonuPriAcl 3 }

		
--  1.3.6.1.4.1.37950.1.1.6.1.6.15.5.4
		-- 1.3.6.1.4.1.37950.1.1.6.1.6.15.5.4
		priAclWanCtl OBJECT-TYPE
			SYNTAX INTEGER
				{
				disable(0),
				enable(1)
				}
			MAX-ACCESS read-write
			STATUS current
			DESCRIPTION
				"Description."
			::= { gonuPriAcl 4 }

		
--  1.3.6.1.4.1.37950.1.1.6.1.6.15.5.5
		-- 1.3.6.1.4.1.37950.1.1.6.1.6.15.5.5
		priAclIPv4Ctl OBJECT-TYPE
			SYNTAX INTEGER
				{
				disable(0),
				enable(1)
				}
			MAX-ACCESS read-write
			STATUS current
			DESCRIPTION
				"Description."
			::= { gonuPriAcl 5 }

		
--  1.3.6.1.4.1.37950.1.1.6.1.6.15.5.6
		-- 1.3.6.1.4.1.37950.1.1.6.1.6.15.5.6
		priAclIPv4Addr OBJECT-TYPE
			SYNTAX IpAddress
			MAX-ACCESS read-write
			STATUS current
			DESCRIPTION
				"Description."
			::= { gonuPriAcl 6 }

		
--  1.3.6.1.4.1.37950.1.1.6.1.6.15.5.7
		-- 1.3.6.1.4.1.37950.1.1.6.1.6.15.5.7
		priAclIPv4Mask OBJECT-TYPE
			SYNTAX IpAddress
			MAX-ACCESS read-write
			STATUS current
			DESCRIPTION
				"Description."
			::= { gonuPriAcl 7 }

		
--  1.3.6.1.4.1.37950.1.1.6.1.6.15.5.8
		-- 1.3.6.1.4.1.37950.1.1.6.1.6.15.5.8
		priAclIPv6Ctl OBJECT-TYPE
			SYNTAX INTEGER
				{
				disable(0),
				enable(1)
				}
			MAX-ACCESS read-write
			STATUS current
			DESCRIPTION
				"Description."
			::= { gonuPriAcl 8 }

		
--  1.3.6.1.4.1.37950.1.1.6.1.6.15.5.9
		-- 1.3.6.1.4.1.37950.1.1.6.1.6.15.5.9
		priAclIPv6Addr OBJECT-TYPE
			SYNTAX OCTET STRING
			MAX-ACCESS read-write
			STATUS current
			DESCRIPTION
				"Description."
			::= { gonuPriAcl 9 }

		
--  1.3.6.1.4.1.37950.1.1.6.1.6.15.5.10
		-- 1.3.6.1.4.1.37950.1.1.6.1.6.15.5.10
		priAclIPv6Pfx OBJECT-TYPE
			SYNTAX Unsigned32
			MAX-ACCESS read-write
			STATUS current
			DESCRIPTION
				"Description."
			::= { gonuPriAcl 10 }

		
--  1.3.6.1.4.1.37950.1.1.6.1.6.15.5.11
		-- 1.3.6.1.4.1.37950.1.1.6.1.6.15.5.11
		priAclPortID OBJECT-TYPE
			SYNTAX Unsigned32 (0..65535)
			MAX-ACCESS read-write
			STATUS current
			DESCRIPTION
				"Description."
			::= { gonuPriAcl 11 }

		
--  1.3.6.1.4.1.37950.1.1.6.1.6.15.5.12
		-- 1.3.6.1.4.1.37950.1.1.6.1.6.15.5.12
		priAclAction OBJECT-TYPE
			SYNTAX INTEGER { submit(1) }
			MAX-ACCESS read-write
			STATUS current
			DESCRIPTION
				"Description."
			::= { gonuPriAcl 12 }

		
--  1.3.6.1.4.1.37950.1.1.6.1.6.16
		-- 1.3.6.1.4.1.37950.1.1.6.1.6.16
		gOnuPriWanConnV6 OBJECT IDENTIFIER ::= { gOnuPriCfg 16 }

		
--  1.3.6.1.4.1.37950.1.1.6.1.6.16.1
		-- 1.3.6.1.4.1.37950.1.1.6.1.6.16.1
		priV6WanConnAdd OBJECT IDENTIFIER ::= { gOnuPriWanConnV6 1 }

		
--  1.3.6.1.4.1.37950.1.1.6.1.6.16.1.1
		-- 1.3.6.1.4.1.37950.1.1.6.1.6.16.1.1
		priV6WanAddPon OBJECT-TYPE
			SYNTAX INTEGER (1..16)
			MAX-ACCESS read-write
			STATUS current
			DESCRIPTION
				"Description."
			::= { priV6WanConnAdd 1 }

		
--  1.3.6.1.4.1.37950.1.1.6.1.6.16.1.2
		-- 1.3.6.1.4.1.37950.1.1.6.1.6.16.1.2
		priV6WanAddOnu OBJECT-TYPE
			SYNTAX INTEGER (1..65535)
			MAX-ACCESS read-write
			STATUS current
			DESCRIPTION
				"Description."
			::= { priV6WanConnAdd 2 }

		
--  1.3.6.1.4.1.37950.1.1.6.1.6.16.1.3
		-- 1.3.6.1.4.1.37950.1.1.6.1.6.16.1.3
		priV6ConnType OBJECT-TYPE
			SYNTAX INTEGER
				{
				bridge(0),
				route(1)
				}
			MAX-ACCESS read-write
			STATUS current
			DESCRIPTION
				"Description."
			::= { priV6WanConnAdd 3 }

		
--  1.3.6.1.4.1.37950.1.1.6.1.6.16.1.4
		-- 1.3.6.1.4.1.37950.1.1.6.1.6.16.1.4
		priV6ConnAddAction OBJECT-TYPE
			SYNTAX INTEGER { add(1) }
			MAX-ACCESS read-write
			STATUS current
			DESCRIPTION
				"Description."
			::= { priV6WanConnAdd 4 }

		
--  1.3.6.1.4.1.37950.1.1.6.1.6.16.2
		-- 1.3.6.1.4.1.37950.1.1.6.1.6.16.2
		priV6WanConnDelete OBJECT IDENTIFIER ::= { gOnuPriWanConnV6 2 }

		
--  1.3.6.1.4.1.37950.1.1.6.1.6.16.2.1
		-- 1.3.6.1.4.1.37950.1.1.6.1.6.16.2.1
		priV6WanDeletePon OBJECT-TYPE
			SYNTAX INTEGER (1..16)
			MAX-ACCESS read-write
			STATUS current
			DESCRIPTION
				"Description."
			::= { priV6WanConnDelete 1 }

		
--  1.3.6.1.4.1.37950.1.1.6.1.6.16.2.2
		-- 1.3.6.1.4.1.37950.1.1.6.1.6.16.2.2
		priV6WanDeleteOnu OBJECT-TYPE
			SYNTAX INTEGER (1..65535)
			MAX-ACCESS read-write
			STATUS current
			DESCRIPTION
				"Description."
			::= { priV6WanConnDelete 2 }

		
--  1.3.6.1.4.1.37950.1.1.6.1.6.16.2.3
		-- 1.3.6.1.4.1.37950.1.1.6.1.6.16.2.3
		priV6ConnIndexD OBJECT-TYPE
			SYNTAX Integer32 (1..8)
			MAX-ACCESS read-write
			STATUS current
			DESCRIPTION
				"Description."
			::= { priV6WanConnDelete 3 }

		
--  1.3.6.1.4.1.37950.1.1.6.1.6.16.2.4
		-- 1.3.6.1.4.1.37950.1.1.6.1.6.16.2.4
		priV6ConnDeleteAction OBJECT-TYPE
			SYNTAX INTEGER { delete(1) }
			MAX-ACCESS read-write
			STATUS current
			DESCRIPTION
				"Description."
			::= { priV6WanConnDelete 4 }

		
--  1.3.6.1.4.1.37950.1.1.6.1.6.16.3
		-- 1.3.6.1.4.1.37950.1.1.6.1.6.16.3
		priV6WanConnCfg OBJECT IDENTIFIER ::= { gOnuPriWanConnV6 3 }

		
--  1.3.6.1.4.1.37950.1.1.6.1.6.16.3.1
		-- 1.3.6.1.4.1.37950.1.1.6.1.6.16.3.1
		priV6ConnPon OBJECT-TYPE
			SYNTAX INTEGER (1..16)
			MAX-ACCESS read-write
			STATUS current
			DESCRIPTION
				"Description."
			::= { priV6WanConnCfg 1 }

		
--  1.3.6.1.4.1.37950.1.1.6.1.6.16.3.2
		-- 1.3.6.1.4.1.37950.1.1.6.1.6.16.3.2
		priV6ConnOnu OBJECT-TYPE
			SYNTAX INTEGER (1..65535)
			MAX-ACCESS read-write
			STATUS current
			DESCRIPTION
				"Description."
			::= { priV6WanConnCfg 2 }

		
--  1.3.6.1.4.1.37950.1.1.6.1.6.16.3.3
		-- 1.3.6.1.4.1.37950.1.1.6.1.6.16.3.3
		priV6ConnIndex OBJECT-TYPE
			SYNTAX INTEGER (1..8)
			MAX-ACCESS read-write
			STATUS current
			DESCRIPTION
				"Description."
			::= { priV6WanConnCfg 3 }

		
--  1.3.6.1.4.1.37950.1.1.6.1.6.16.3.4
		-- 1.3.6.1.4.1.37950.1.1.6.1.6.16.3.4
		priV6ConnBindLan OBJECT-TYPE
			SYNTAX INTEGER (0..65535)
			MAX-ACCESS read-write
			STATUS current
			DESCRIPTION
				"Description."
			::= { priV6WanConnCfg 4 }

		
--  1.3.6.1.4.1.37950.1.1.6.1.6.16.3.5
		-- 1.3.6.1.4.1.37950.1.1.6.1.6.16.3.5
		priV6ConnBindSsid OBJECT-TYPE
			SYNTAX INTEGER (0..65535)
			MAX-ACCESS read-write
			STATUS current
			DESCRIPTION
				"Description."
			::= { priV6WanConnCfg 5 }

		
--  1.3.6.1.4.1.37950.1.1.6.1.6.16.3.6
		-- 1.3.6.1.4.1.37950.1.1.6.1.6.16.3.6
		priV6WanMode OBJECT-TYPE
			SYNTAX INTEGER
				{
				internet(0),
				multicast(1),
				tr069(2),
				tr069_internet(3),
				tr069_voip(4),
				voip_internet(5),
				tr069_voip_internet(6),
				voip(7),
				other(100)
				}
			MAX-ACCESS read-write
			STATUS current
			DESCRIPTION
				"Description."
			::= { priV6WanConnCfg 6 }

		
--  1.3.6.1.4.1.37950.1.1.6.1.6.16.3.7
		-- 1.3.6.1.4.1.37950.1.1.6.1.6.16.3.7
		priV6ConnTypeCfg OBJECT-TYPE
			SYNTAX INTEGER
				{
				bridge(0),
				route(1)
				}
			MAX-ACCESS read-write
			STATUS current
			DESCRIPTION
				"Description."
			::= { priV6WanConnCfg 7 }

		
--  1.3.6.1.4.1.37950.1.1.6.1.6.16.3.8
		-- 1.3.6.1.4.1.37950.1.1.6.1.6.16.3.8
		priV6ConnVlanId OBJECT-TYPE
			SYNTAX Integer32 (0..4095)
			MAX-ACCESS read-write
			STATUS current
			DESCRIPTION
				"Description."
			::= { priV6WanConnCfg 8 }

		
--  1.3.6.1.4.1.37950.1.1.6.1.6.16.3.9
		-- 1.3.6.1.4.1.37950.1.1.6.1.6.16.3.9
		priV6ConnVlanCos OBJECT-TYPE
			SYNTAX INTEGER (0..7)
			MAX-ACCESS read-write
			STATUS current
			DESCRIPTION
				"Description."
			::= { priV6WanConnCfg 9 }

		
--  1.3.6.1.4.1.37950.1.1.6.1.6.16.3.10
		-- 1.3.6.1.4.1.37950.1.1.6.1.6.16.3.10
		priV6ConnIpProtocol OBJECT-TYPE
			SYNTAX INTEGER
				{
				ipv4(0),
				ipv6(1),
				ipv4_ipv6(2)
				}
			MAX-ACCESS read-write
			STATUS current
			DESCRIPTION
				"Description."
			::= { priV6WanConnCfg 10 }

		
--  1.3.6.1.4.1.37950.1.1.6.1.6.16.3.11
		-- 1.3.6.1.4.1.37950.1.1.6.1.6.16.3.11
		priV6ConnModeCfg OBJECT-TYPE
			SYNTAX INTEGER
				{
				dhcp(0),
				static(1),
				pppoe(2)
				}
			MAX-ACCESS read-write
			STATUS current
			DESCRIPTION
				"Description."
			::= { priV6WanConnCfg 11 }

		
--  1.3.6.1.4.1.37950.1.1.6.1.6.16.3.12
		-- 1.3.6.1.4.1.37950.1.1.6.1.6.16.3.12
		priV6ConnIpAddressIpv4 OBJECT-TYPE
			SYNTAX IpAddress
			MAX-ACCESS read-write
			STATUS current
			DESCRIPTION
				"Description."
			::= { priV6WanConnCfg 12 }

		
--  1.3.6.1.4.1.37950.1.1.6.1.6.16.3.13
		-- 1.3.6.1.4.1.37950.1.1.6.1.6.16.3.13
		priV6ConnIpNetMaskIpv4 OBJECT-TYPE
			SYNTAX IpAddress
			MAX-ACCESS read-write
			STATUS current
			DESCRIPTION
				"Description."
			::= { priV6WanConnCfg 13 }

		
--  1.3.6.1.4.1.37950.1.1.6.1.6.16.3.14
		-- 1.3.6.1.4.1.37950.1.1.6.1.6.16.3.14
		priV6ConnGatewayIpv4 OBJECT-TYPE
			SYNTAX IpAddress
			MAX-ACCESS read-write
			STATUS current
			DESCRIPTION
				"Description."
			::= { priV6WanConnCfg 14 }

		
--  1.3.6.1.4.1.37950.1.1.6.1.6.16.3.15
		-- 1.3.6.1.4.1.37950.1.1.6.1.6.16.3.15
		priV6ConnDnsEnableIpv4 OBJECT-TYPE
			SYNTAX INTEGER
				{
				disable(0),
				enable(1)
				}
			MAX-ACCESS read-write
			STATUS current
			DESCRIPTION
				"Description."
			::= { priV6WanConnCfg 15 }

		
--  1.3.6.1.4.1.37950.1.1.6.1.6.16.3.16
		-- 1.3.6.1.4.1.37950.1.1.6.1.6.16.3.16
		priV6ConnMasterDnsIpv4 OBJECT-TYPE
			SYNTAX IpAddress
			MAX-ACCESS read-write
			STATUS current
			DESCRIPTION
				"Description."
			::= { priV6WanConnCfg 16 }

		
--  1.3.6.1.4.1.37950.1.1.6.1.6.16.3.17
		-- 1.3.6.1.4.1.37950.1.1.6.1.6.16.3.17
		priV6ConnSlaveDnsIpv4 OBJECT-TYPE
			SYNTAX IpAddress
			MAX-ACCESS read-write
			STATUS current
			DESCRIPTION
				"Description."
			::= { priV6WanConnCfg 17 }

		
--  1.3.6.1.4.1.37950.1.1.6.1.6.16.3.18
		-- 1.3.6.1.4.1.37950.1.1.6.1.6.16.3.18
		priV6ConnNatEnable OBJECT-TYPE
			SYNTAX INTEGER
				{
				disable(0),
				enable(1)
				}
			MAX-ACCESS read-write
			STATUS current
			DESCRIPTION
				"Description."
			::= { priV6WanConnCfg 18 }

		
--  1.3.6.1.4.1.37950.1.1.6.1.6.16.3.19
		-- 1.3.6.1.4.1.37950.1.1.6.1.6.16.3.19
		priV6ConnAddressIpv6 OBJECT-TYPE
			SYNTAX OCTET STRING
			MAX-ACCESS read-write
			STATUS current
			DESCRIPTION
				"Description."
			::= { priV6WanConnCfg 19 }

		
--  1.3.6.1.4.1.37950.1.1.6.1.6.16.3.20
		-- 1.3.6.1.4.1.37950.1.1.6.1.6.16.3.20
		priV6ConnPrefixLenIpv6 OBJECT-TYPE
			SYNTAX INTEGER (0..128)
			MAX-ACCESS read-write
			STATUS current
			DESCRIPTION
				"Description."
			::= { priV6WanConnCfg 20 }

		
--  1.3.6.1.4.1.37950.1.1.6.1.6.16.3.21
		-- 1.3.6.1.4.1.37950.1.1.6.1.6.16.3.21
		priV6ConnGatewayIpv6 OBJECT-TYPE
			SYNTAX OCTET STRING
			MAX-ACCESS read-write
			STATUS current
			DESCRIPTION
				"Description."
			::= { priV6WanConnCfg 21 }

		
--  1.3.6.1.4.1.37950.1.1.6.1.6.16.3.22
		-- 1.3.6.1.4.1.37950.1.1.6.1.6.16.3.22
		priV6ConnDnsEnableIpv6 OBJECT-TYPE
			SYNTAX INTEGER
				{
				disable(0),
				enable(1)
				}
			MAX-ACCESS read-write
			STATUS current
			DESCRIPTION
				"Description."
			::= { priV6WanConnCfg 22 }

		
--  1.3.6.1.4.1.37950.1.1.6.1.6.16.3.23
		-- 1.3.6.1.4.1.37950.1.1.6.1.6.16.3.23
		priV6ConnMasterDnsIpv6 OBJECT-TYPE
			SYNTAX OCTET STRING
			MAX-ACCESS read-write
			STATUS current
			DESCRIPTION
				"Description."
			::= { priV6WanConnCfg 23 }

		
--  1.3.6.1.4.1.37950.1.1.6.1.6.16.3.24
		-- 1.3.6.1.4.1.37950.1.1.6.1.6.16.3.24
		priV6ConnSlaveDnsIpv6 OBJECT-TYPE
			SYNTAX OCTET STRING
			MAX-ACCESS read-write
			STATUS current
			DESCRIPTION
				"Description."
			::= { priV6WanConnCfg 24 }

		
--  1.3.6.1.4.1.37950.1.1.6.1.6.16.3.25
		-- 1.3.6.1.4.1.37950.1.1.6.1.6.16.3.25
		priV6ConnSlaac OBJECT-TYPE
			SYNTAX INTEGER
				{
				disable(0),
				enable(1)
				}
			MAX-ACCESS read-write
			STATUS current
			DESCRIPTION
				"Description."
			::= { priV6WanConnCfg 25 }

		
--  1.3.6.1.4.1.37950.1.1.6.1.6.16.3.26
		-- 1.3.6.1.4.1.37950.1.1.6.1.6.16.3.26
		priV6ConnPppoeProxy OBJECT-TYPE
			SYNTAX INTEGER
				{
				disable(0),
				enable(1)
				}
			MAX-ACCESS read-write
			STATUS current
			DESCRIPTION
				"Description."
			::= { priV6WanConnCfg 26 }

		
--  1.3.6.1.4.1.37950.1.1.6.1.6.16.3.27
		-- 1.3.6.1.4.1.37950.1.1.6.1.6.16.3.27
		priV6ConnPppoeUsername OBJECT-TYPE
			SYNTAX OCTET STRING
			MAX-ACCESS read-write
			STATUS current
			DESCRIPTION
				"Description."
			::= { priV6WanConnCfg 27 }

		
--  1.3.6.1.4.1.37950.1.1.6.1.6.16.3.28
		-- 1.3.6.1.4.1.37950.1.1.6.1.6.16.3.28
		priV6ConnPppoePassword OBJECT-TYPE
			SYNTAX OCTET STRING
			MAX-ACCESS read-write
			STATUS current
			DESCRIPTION
				"Description."
			::= { priV6WanConnCfg 28 }

		
--  1.3.6.1.4.1.37950.1.1.6.1.6.16.3.29
		-- 1.3.6.1.4.1.37950.1.1.6.1.6.16.3.29
		priV6ConnPppoeSerName OBJECT-TYPE
			SYNTAX OCTET STRING
			MAX-ACCESS read-write
			STATUS current
			DESCRIPTION
				"Description."
			::= { priV6WanConnCfg 29 }

		
--  1.3.6.1.4.1.37950.1.1.6.1.6.16.3.30
		-- 1.3.6.1.4.1.37950.1.1.6.1.6.16.3.30
		priV6ConnPppoeMode OBJECT-TYPE
			SYNTAX INTEGER
				{
				autoConnect(0),
				flowConnect(1)
				}
			MAX-ACCESS read-write
			STATUS current
			DESCRIPTION
				"Description."
			::= { priV6WanConnCfg 30 }

		
--  1.3.6.1.4.1.37950.1.1.6.1.6.16.3.31
		-- 1.3.6.1.4.1.37950.1.1.6.1.6.16.3.31
		priV6ConnDhcpv6ClientAddress OBJECT-TYPE
			SYNTAX INTEGER
				{
				disable(0),
				enable(1)
				}
			MAX-ACCESS read-write
			STATUS current
			DESCRIPTION
				"Description."
			::= { priV6WanConnCfg 31 }

		
--  1.3.6.1.4.1.37950.1.1.6.1.6.16.3.32
		-- 1.3.6.1.4.1.37950.1.1.6.1.6.16.3.32
		priV6ConnDhcpv6ClientPrefix OBJECT-TYPE
			SYNTAX INTEGER
				{
				disable(0),
				enable(1)
				}
			MAX-ACCESS read-write
			STATUS current
			DESCRIPTION
				"Description."
			::= { priV6WanConnCfg 32 }

		
--  1.3.6.1.4.1.37950.1.1.6.1.6.16.3.33
		-- 1.3.6.1.4.1.37950.1.1.6.1.6.16.3.33
		priV6ConnDsLiteEnable OBJECT-TYPE
			SYNTAX INTEGER
				{
				disable(0),
				enable(1)
				}
			MAX-ACCESS read-write
			STATUS current
			DESCRIPTION
				"Description."
			::= { priV6WanConnCfg 33 }

		
--  1.3.6.1.4.1.37950.1.1.6.1.6.16.3.34
		-- 1.3.6.1.4.1.37950.1.1.6.1.6.16.3.34
		priV6ConnDsLiteAftrMode OBJECT-TYPE
			SYNTAX INTEGER
				{
				dhcpv6(0),
				manual(1)
				}
			MAX-ACCESS read-write
			STATUS current
			DESCRIPTION
				"Description."
			::= { priV6WanConnCfg 34 }

		
--  1.3.6.1.4.1.37950.1.1.6.1.6.16.3.35
		-- 1.3.6.1.4.1.37950.1.1.6.1.6.16.3.35
		priV6ConnDsLiteAddressType OBJECT-TYPE
			SYNTAX INTEGER
				{
				ipv6(0),
				dns(1)
				}
			MAX-ACCESS read-write
			STATUS current
			DESCRIPTION
				"Description."
			::= { priV6WanConnCfg 35 }

		
--  1.3.6.1.4.1.37950.1.1.6.1.6.16.3.36
		-- 1.3.6.1.4.1.37950.1.1.6.1.6.16.3.36
		priV6ConnDsLiteAddress OBJECT-TYPE
			SYNTAX OCTET STRING
			MAX-ACCESS read-write
			STATUS current
			DESCRIPTION
				"Description."
			::= { priV6WanConnCfg 36 }

		
--  1.3.6.1.4.1.37950.1.1.6.1.6.16.3.37
		-- 1.3.6.1.4.1.37950.1.1.6.1.6.16.3.37
		priV6ConnQosEnable OBJECT-TYPE
			SYNTAX INTEGER
				{
				disable(0),
				enable(1)
				}
			MAX-ACCESS read-write
			STATUS current
			DESCRIPTION
				"Description."
			::= { priV6WanConnCfg 37 }

		
--  1.3.6.1.4.1.37950.1.1.6.1.6.16.3.38
		-- 1.3.6.1.4.1.37950.1.1.6.1.6.16.3.38
		priV6ConnVlanMode OBJECT-TYPE
			SYNTAX INTEGER
				{
				disable(0),
				tag(1),
				transparent(2)
				}
			MAX-ACCESS read-write
			STATUS current
			DESCRIPTION
				"Description."
			::= { priV6WanConnCfg 38 }

		
--  1.3.6.1.4.1.37950.1.1.6.1.6.16.3.39
		-- 1.3.6.1.4.1.37950.1.1.6.1.6.16.3.39
		priV6ConnTranslationEnable OBJECT-TYPE
			SYNTAX INTEGER
				{
				disable(0),
				enable(1)
				}
			MAX-ACCESS read-write
			STATUS current
			DESCRIPTION
				"Description."
			::= { priV6WanConnCfg 39 }

		
--  1.3.6.1.4.1.37950.1.1.6.1.6.16.3.40
		-- 1.3.6.1.4.1.37950.1.1.6.1.6.16.3.40
		priV6ConnTranslationVlan OBJECT-TYPE
			SYNTAX INTEGER (1..4095)
			MAX-ACCESS read-write
			STATUS current
			DESCRIPTION
				"Description."
			::= { priV6WanConnCfg 40 }

		
--  1.3.6.1.4.1.37950.1.1.6.1.6.16.3.41
		-- 1.3.6.1.4.1.37950.1.1.6.1.6.16.3.41
		priV6ConnTranslationCos OBJECT-TYPE
			SYNTAX INTEGER (0..7)
			MAX-ACCESS read-write
			STATUS current
			DESCRIPTION
				"Description."
			::= { priV6WanConnCfg 41 }

		
--  1.3.6.1.4.1.37950.1.1.6.1.6.16.3.42
		-- 1.3.6.1.4.1.37950.1.1.6.1.6.16.3.42
		priV6ConnQinqEnable OBJECT-TYPE
			SYNTAX INTEGER
				{
				disable(0),
				enable(1)
				}
			MAX-ACCESS read-write
			STATUS current
			DESCRIPTION
				"Description."
			::= { priV6WanConnCfg 42 }

		
--  1.3.6.1.4.1.37950.1.1.6.1.6.16.3.43
		-- 1.3.6.1.4.1.37950.1.1.6.1.6.16.3.43
		priV6ConnQinqTpid OBJECT-TYPE
			SYNTAX Integer32 (1..65534)
			MAX-ACCESS read-write
			STATUS current
			DESCRIPTION
				"Description."
			::= { priV6WanConnCfg 43 }

		
--  1.3.6.1.4.1.37950.1.1.6.1.6.16.3.44
		-- 1.3.6.1.4.1.37950.1.1.6.1.6.16.3.44
		priV6ConnSvlanId OBJECT-TYPE
			SYNTAX INTEGER (1..4095)
			MAX-ACCESS read-write
			STATUS current
			DESCRIPTION
				"Description."
			::= { priV6WanConnCfg 44 }

		
--  1.3.6.1.4.1.37950.1.1.6.1.6.16.3.45
		-- 1.3.6.1.4.1.37950.1.1.6.1.6.16.3.45
		priV6ConnSvlanCos OBJECT-TYPE
			SYNTAX INTEGER (0..7)
			MAX-ACCESS read-write
			STATUS current
			DESCRIPTION
				"Description."
			::= { priV6WanConnCfg 45 }

		
--  1.3.6.1.4.1.37950.1.1.6.1.6.16.3.46
		-- 1.3.6.1.4.1.37950.1.1.6.1.6.16.3.46
		priV6ConnRouteMtu OBJECT-TYPE
			SYNTAX Integer32 (0 | 576..1500)
			MAX-ACCESS read-write
			STATUS current
			DESCRIPTION
				"Description."
			::= { priV6WanConnCfg 46 }

		
--  1.3.6.1.4.1.37950.1.1.6.1.6.16.3.47
		-- 1.3.6.1.4.1.37950.1.1.6.1.6.16.3.47
		priV6ConnCfgAction OBJECT-TYPE
			SYNTAX INTEGER { commit(1) }
			MAX-ACCESS read-write
			STATUS current
			DESCRIPTION
				"Description."
			::= { priV6WanConnCfg 47 }

		
--  1.3.6.1.4.1.37950.1.1.6.1.6.16.4
		-- 1.3.6.1.4.1.37950.1.1.6.1.6.16.4
		priV6WanConnCommit OBJECT IDENTIFIER ::= { gOnuPriWanConnV6 4 }

		
--  1.3.6.1.4.1.37950.1.1.6.1.6.16.4.1
		-- 1.3.6.1.4.1.37950.1.1.6.1.6.16.4.1
		priV6ConnCommitPon OBJECT-TYPE
			SYNTAX INTEGER (1..16)
			MAX-ACCESS read-write
			STATUS current
			DESCRIPTION
				"Description."
			::= { priV6WanConnCommit 1 }

		
--  1.3.6.1.4.1.37950.1.1.6.1.6.16.4.2
		-- 1.3.6.1.4.1.37950.1.1.6.1.6.16.4.2
		priV6ConnCommitOnu OBJECT-TYPE
			SYNTAX INTEGER (1..65535)
			MAX-ACCESS read-write
			STATUS current
			DESCRIPTION
				"Description."
			::= { priV6WanConnCommit 2 }

		
--  1.3.6.1.4.1.37950.1.1.6.1.6.16.4.3
		-- 1.3.6.1.4.1.37950.1.1.6.1.6.16.4.3
		priV6ConnCommitAction OBJECT-TYPE
			SYNTAX INTEGER { commit(1) }
			MAX-ACCESS read-write
			STATUS current
			DESCRIPTION
				"Description."
			::= { priV6WanConnCommit 3 }

		
--  1.3.6.1.4.1.37950.1.1.6.1.6.17
		-- 1.3.6.1.4.1.37950.1.1.6.1.6.17
		gOnuPriDhcpServerV6 OBJECT IDENTIFIER ::= { gOnuPriCfg 17 }

		
--  1.3.6.1.4.1.37950.1.1.6.1.6.17.1
		-- 1.3.6.1.4.1.37950.1.1.6.1.6.17.1
		onuPriDhcpv6ServerPon OBJECT-TYPE
			SYNTAX Integer32 (1..16)
			MAX-ACCESS read-write
			STATUS current
			DESCRIPTION
				"Description."
			::= { gOnuPriDhcpServerV6 1 }

		
--  1.3.6.1.4.1.37950.1.1.6.1.6.17.2
		-- 1.3.6.1.4.1.37950.1.1.6.1.6.17.2
		onuPriDhcpv6ServerOnu OBJECT-TYPE
			SYNTAX Integer32 (1..65535)
			MAX-ACCESS read-write
			STATUS current
			DESCRIPTION
				"Description."
			::= { gOnuPriDhcpServerV6 2 }

		
--  1.3.6.1.4.1.37950.1.1.6.1.6.17.3
		-- 1.3.6.1.4.1.37950.1.1.6.1.6.17.3
		onuPriDhcpv6LanIp OBJECT-TYPE
			SYNTAX OCTET STRING
			MAX-ACCESS read-write
			STATUS current
			DESCRIPTION
				"Description."
			::= { gOnuPriDhcpServerV6 3 }

		
--  1.3.6.1.4.1.37950.1.1.6.1.6.17.4
		-- 1.3.6.1.4.1.37950.1.1.6.1.6.17.4
		onuPriDhcpv6LanPrefixlen OBJECT-TYPE
			SYNTAX INTEGER (48..64)
			MAX-ACCESS read-write
			STATUS current
			DESCRIPTION
				"Description."
			::= { gOnuPriDhcpServerV6 4 }

		
--  1.3.6.1.4.1.37950.1.1.6.1.6.17.5
		-- 1.3.6.1.4.1.37950.1.1.6.1.6.17.5
		onuPriDhcpv6PrefixMode OBJECT-TYPE
			SYNTAX INTEGER
				{
				wan_delegated(0),
				static(1),
				auto(2)
				}
			MAX-ACCESS read-write
			STATUS current
			DESCRIPTION
				"Description."
			::= { gOnuPriDhcpServerV6 5 }

		
--  1.3.6.1.4.1.37950.1.1.6.1.6.17.6
		-- 1.3.6.1.4.1.37950.1.1.6.1.6.17.6
		onuPriDhcpv6PrefixModeIp OBJECT-TYPE
			SYNTAX OCTET STRING
			MAX-ACCESS read-write
			STATUS current
			DESCRIPTION
				"Description."
			::= { gOnuPriDhcpServerV6 6 }

		
--  1.3.6.1.4.1.37950.1.1.6.1.6.17.7
		-- 1.3.6.1.4.1.37950.1.1.6.1.6.17.7
		onuPriDhcpv6Enable OBJECT-TYPE
			SYNTAX INTEGER
				{
				disable(0),
				enable(1),
				relay(2)
				}
			MAX-ACCESS read-write
			STATUS current
			DESCRIPTION
				"Description."
			::= { gOnuPriDhcpServerV6 7 }

		
--  1.3.6.1.4.1.37950.1.1.6.1.6.17.8
		-- 1.3.6.1.4.1.37950.1.1.6.1.6.17.8
		onuPriDhcpv6Preference OBJECT-TYPE
			SYNTAX Unsigned32 (0..4294967295)
			MAX-ACCESS read-write
			STATUS current
			DESCRIPTION
				"Description."
			::= { gOnuPriDhcpServerV6 8 }

		
--  1.3.6.1.4.1.37950.1.1.6.1.6.17.9
		-- 1.3.6.1.4.1.37950.1.1.6.1.6.17.9
		onuPriDhcpv6BeginIp OBJECT-TYPE
			SYNTAX OCTET STRING
			MAX-ACCESS read-write
			STATUS current
			DESCRIPTION
				"Description."
			::= { gOnuPriDhcpServerV6 9 }

		
--  1.3.6.1.4.1.37950.1.1.6.1.6.17.10
		-- 1.3.6.1.4.1.37950.1.1.6.1.6.17.10
		onuPriDhcpv6EndIp OBJECT-TYPE
			SYNTAX OCTET STRING
			MAX-ACCESS read-write
			STATUS current
			DESCRIPTION
				"Description."
			::= { gOnuPriDhcpServerV6 10 }

		
--  1.3.6.1.4.1.37950.1.1.6.1.6.17.11
		-- 1.3.6.1.4.1.37950.1.1.6.1.6.17.11
		onuPriDhcpv6PoolType OBJECT-TYPE
			SYNTAX INTEGER
				{
				pc(0),
				camera(1),
				stb(2),
				ip_phone(3)
				}
			MAX-ACCESS read-write
			STATUS current
			DESCRIPTION
				"Description."
			::= { gOnuPriDhcpServerV6 11 }

		
--  1.3.6.1.4.1.37950.1.1.6.1.6.17.12
		-- 1.3.6.1.4.1.37950.1.1.6.1.6.17.12
		onuPriDhcpv6MasterDns OBJECT-TYPE
			SYNTAX OCTET STRING
			MAX-ACCESS read-write
			STATUS current
			DESCRIPTION
				"Description."
			::= { gOnuPriDhcpServerV6 12 }

		
--  1.3.6.1.4.1.37950.1.1.6.1.6.17.13
		-- 1.3.6.1.4.1.37950.1.1.6.1.6.17.13
		onuPriDhcpv6SlaveDns OBJECT-TYPE
			SYNTAX OCTET STRING
			MAX-ACCESS read-write
			STATUS current
			DESCRIPTION
				"Description."
			::= { gOnuPriDhcpServerV6 13 }

		
--  1.3.6.1.4.1.37950.1.1.6.1.6.17.14
		-- 1.3.6.1.4.1.37950.1.1.6.1.6.17.14
		onuPriDhcpv6Gateway OBJECT-TYPE
			SYNTAX OCTET STRING
			MAX-ACCESS read-write
			STATUS current
			DESCRIPTION
				"Description."
			::= { gOnuPriDhcpServerV6 14 }

		
--  1.3.6.1.4.1.37950.1.1.6.1.6.17.15
		-- 1.3.6.1.4.1.37950.1.1.6.1.6.17.15
		onuPriDhcpv6RelayIp OBJECT-TYPE
			SYNTAX OCTET STRING
			MAX-ACCESS read-write
			STATUS current
			DESCRIPTION
				"Description."
			::= { gOnuPriDhcpServerV6 15 }

		
--  1.3.6.1.4.1.37950.1.1.6.1.6.17.16
		-- 1.3.6.1.4.1.37950.1.1.6.1.6.17.16
		onuPriDhcpv6RA OBJECT-TYPE
			SYNTAX INTEGER
				{
				disable(0),
				enable(1)
				}
			MAX-ACCESS read-write
			STATUS current
			DESCRIPTION
				"Description."
			::= { gOnuPriDhcpServerV6 16 }

		
--  1.3.6.1.4.1.37950.1.1.6.1.6.17.17
		-- 1.3.6.1.4.1.37950.1.1.6.1.6.17.17
		onuPriDhcpv6RAManage OBJECT-TYPE
			SYNTAX INTEGER
				{
				disable(0),
				enable(1)
				}
			MAX-ACCESS read-write
			STATUS current
			DESCRIPTION
				"Description."
			::= { gOnuPriDhcpServerV6 17 }

		
--  1.3.6.1.4.1.37950.1.1.6.1.6.17.18
		-- 1.3.6.1.4.1.37950.1.1.6.1.6.17.18
		onuPriDhcpv6RAOther OBJECT-TYPE
			SYNTAX INTEGER
				{
				disable(0),
				enable(1)
				}
			MAX-ACCESS read-write
			STATUS current
			DESCRIPTION
				"Description."
			::= { gOnuPriDhcpServerV6 18 }

		
--  1.3.6.1.4.1.37950.1.1.6.1.6.17.19
		-- 1.3.6.1.4.1.37950.1.1.6.1.6.17.19
		onuPriDhcpv6RAMaxInterval OBJECT-TYPE
			SYNTAX Integer32 (1..1800)
			MAX-ACCESS read-write
			STATUS current
			DESCRIPTION
				"Description."
			::= { gOnuPriDhcpServerV6 19 }

		
--  1.3.6.1.4.1.37950.1.1.6.1.6.17.20
		-- 1.3.6.1.4.1.37950.1.1.6.1.6.17.20
		onuPriDhcpv6RAMinInterval OBJECT-TYPE
			SYNTAX Integer32 (1..1800)
			MAX-ACCESS read-write
			STATUS current
			DESCRIPTION
				"Description."
			::= { gOnuPriDhcpServerV6 20 }

		
--  1.3.6.1.4.1.37950.1.1.6.1.6.17.21
		-- 1.3.6.1.4.1.37950.1.1.6.1.6.17.21
		onuPriDhcpv6Action OBJECT-TYPE
			SYNTAX INTEGER
				{
				commit(1),
				remove(2)
				}
			MAX-ACCESS read-write
			STATUS current
			DESCRIPTION
				"Description."
			::= { gOnuPriDhcpServerV6 21 }

		
--  1.3.6.1.4.1.37950.1.1.6.1.6.17.22
		-- 1.3.6.1.4.1.37950.1.1.6.1.6.17.22
		onuPriDhcpv6Valid OBJECT-TYPE
			SYNTAX Unsigned32 (0..4294967295)
			MAX-ACCESS read-write
			STATUS current
			DESCRIPTION
				"Description."
			::= { gOnuPriDhcpServerV6 22 }

		
--  1.3.6.1.4.1.37950.1.1.6.1.6.17.23
		-- 1.3.6.1.4.1.37950.1.1.6.1.6.17.23
		onuPriDhcpv6PrefixModeWanIndex OBJECT-TYPE
			SYNTAX Integer32 (1..8)
			MAX-ACCESS read-write
			STATUS current
			DESCRIPTION
				"Description."
			::= { gOnuPriDhcpServerV6 23 }

		
--  1.3.6.1.4.1.37950.1.1.6.1.6.17.24
		-- 1.3.6.1.4.1.37950.1.1.6.1.6.17.24
		onuPriDhcpv6DNSMode OBJECT-TYPE
			SYNTAX INTEGER
				{
				wanconnection(0),
				static(1),
				hgwproxy(2)
				}
			MAX-ACCESS read-write
			STATUS current
			DESCRIPTION
				"Description."
			::= { gOnuPriDhcpServerV6 24 }

		
--  1.3.6.1.4.1.37950.1.1.6.1.6.17.25
		-- 1.3.6.1.4.1.37950.1.1.6.1.6.17.25
		onuPriDhcpv6DNSModeWanIndex OBJECT-TYPE
			SYNTAX Integer32 (1..8)
			MAX-ACCESS read-write
			STATUS current
			DESCRIPTION
				"Description."
			::= { gOnuPriDhcpServerV6 25 }

		
--  1.3.6.1.4.1.37950.1.1.6.1.6.18
		-- 1.3.6.1.4.1.37950.1.1.6.1.6.18
		gOnuPriLoopChk OBJECT IDENTIFIER ::= { gOnuPriCfg 18 }

		
--  1.3.6.1.4.1.37950.1.1.6.1.6.18.1
		-- 1.3.6.1.4.1.37950.1.1.6.1.6.18.1
		gOnuPriLCPon OBJECT-TYPE
			SYNTAX Integer32
			MAX-ACCESS read-write
			STATUS current
			DESCRIPTION
				"Description."
			::= { gOnuPriLoopChk 1 }

		
--  1.3.6.1.4.1.37950.1.1.6.1.6.18.2
		-- 1.3.6.1.4.1.37950.1.1.6.1.6.18.2
		gOnuPriLCOnu OBJECT-TYPE
			SYNTAX Integer32
			MAX-ACCESS read-write
			STATUS current
			DESCRIPTION
				"Description."
			::= { gOnuPriLoopChk 2 }

		
--  1.3.6.1.4.1.37950.1.1.6.1.6.18.3
		-- 1.3.6.1.4.1.37950.1.1.6.1.6.18.3
		gOnuPriLCStatus OBJECT-TYPE
			SYNTAX INTEGER
				{
				disable(0),
				enable(1)
				}
			MAX-ACCESS read-write
			STATUS current
			DESCRIPTION
				"Description."
			::= { gOnuPriLoopChk 3 }

		
--  1.3.6.1.4.1.37950.1.1.6.1.6.18.4
		-- 1.3.6.1.4.1.37950.1.1.6.1.6.18.4
		gOnuPriLCCheckInterval OBJECT-TYPE
			SYNTAX Integer32 (1..60000)
			MAX-ACCESS read-write
			STATUS current
			DESCRIPTION
				"Description."
			DEFVAL { 1000 }
			::= { gOnuPriLoopChk 4 }

		
--  1.3.6.1.4.1.37950.1.1.6.1.6.18.5
		-- 1.3.6.1.4.1.37950.1.1.6.1.6.18.5
		gOnuPriLCRecoverInterval OBJECT-TYPE
			SYNTAX Integer32 (1..1800)
			MAX-ACCESS read-write
			STATUS current
			DESCRIPTION
				"Description."
			DEFVAL { 60 }
			::= { gOnuPriLoopChk 5 }

		
--  1.3.6.1.4.1.37950.1.1.6.1.6.18.6
		-- 1.3.6.1.4.1.37950.1.1.6.1.6.18.6
		gOnuPriLCEthernetType OBJECT-TYPE
			SYNTAX OCTET STRING
			MAX-ACCESS read-write
			STATUS current
			DESCRIPTION
				"Description."
			DEFVAL { "fffa" }
			::= { gOnuPriLoopChk 6 }

		
--  1.3.6.1.4.1.37950.1.1.6.1.6.18.7
		-- 1.3.6.1.4.1.37950.1.1.6.1.6.18.7
		gOnuPriLCVlan OBJECT-TYPE
			SYNTAX Integer32 (0..4094)
			MAX-ACCESS read-write
			STATUS current
			DESCRIPTION
				"Description."
			DEFVAL { 0 }
			::= { gOnuPriLoopChk 7 }

		
--  1.3.6.1.4.1.37950.1.1.6.1.6.18.8
		-- 1.3.6.1.4.1.37950.1.1.6.1.6.18.8
		gOnuPriLCDestMacType OBJECT-TYPE
			SYNTAX INTEGER
				{
				broadcast_address(0),
				bpdu_address(1)
				}
			MAX-ACCESS read-write
			STATUS current
			DESCRIPTION
				"Description."
			::= { gOnuPriLoopChk 8 }

		
--  1.3.6.1.4.1.37950.1.1.6.1.6.18.9
		-- 1.3.6.1.4.1.37950.1.1.6.1.6.18.9
		gOnuPriLCPortClosingTime OBJECT-TYPE
			SYNTAX Integer32 (1..1800)
			MAX-ACCESS read-write
			STATUS current
			DESCRIPTION
				"Description."
			DEFVAL { 60 }
			::= { gOnuPriLoopChk 9 }

		
--  1.3.6.1.4.1.37950.1.1.6.1.6.18.10
		-- 1.3.6.1.4.1.37950.1.1.6.1.6.18.10
		gOnuPriLCAlarm OBJECT-TYPE
			SYNTAX INTEGER
				{
				disable(0),
				enable(1)
				}
			MAX-ACCESS read-write
			STATUS current
			DESCRIPTION
				"Description."
			::= { gOnuPriLoopChk 10 }

		
--  1.3.6.1.4.1.37950.1.1.6.1.6.18.11
		-- 1.3.6.1.4.1.37950.1.1.6.1.6.18.11
		gOnuPriLCPortdislooped OBJECT-TYPE
			SYNTAX INTEGER
				{
				disable(0),
				enable(1)
				}
			MAX-ACCESS read-write
			STATUS current
			DESCRIPTION
				"Description."
			::= { gOnuPriLoopChk 11 }

		
--  1.3.6.1.4.1.37950.1.1.6.1.6.18.12
		-- 1.3.6.1.4.1.37950.1.1.6.1.6.18.12
		gOnuPriLCAction OBJECT-TYPE
			SYNTAX INTEGER { submit(1) }
			MAX-ACCESS read-write
			STATUS current
			DESCRIPTION
				"Description."
			::= { gOnuPriLoopChk 12 }

		
--  1.3.6.1.4.1.37950.1.1.6.1.6.19
		-- 1.3.6.1.4.1.37950.1.1.6.1.6.19
		gOnuPriTr069 OBJECT IDENTIFIER ::= { gOnuPriCfg 19 }

		
--  1.3.6.1.4.1.37950.1.1.6.1.6.19.1
		-- 1.3.6.1.4.1.37950.1.1.6.1.6.19.1
		onuPriTr069Manage OBJECT IDENTIFIER ::= { gOnuPriTr069 1 }

		
--  1.3.6.1.4.1.37950.1.1.6.1.6.19.1.1
		-- 1.3.6.1.4.1.37950.1.1.6.1.6.19.1.1
		priMngPonID OBJECT-TYPE
			SYNTAX Integer32
			MAX-ACCESS read-write
			STATUS current
			DESCRIPTION
				"Description."
			::= { onuPriTr069Manage 1 }

		
--  1.3.6.1.4.1.37950.1.1.6.1.6.19.1.2
		-- 1.3.6.1.4.1.37950.1.1.6.1.6.19.1.2
		priMngOnuID OBJECT-TYPE
			SYNTAX Integer32
			MAX-ACCESS read-write
			STATUS current
			DESCRIPTION
				"Description."
			::= { onuPriTr069Manage 2 }

		
--  1.3.6.1.4.1.37950.1.1.6.1.6.19.1.3
		-- 1.3.6.1.4.1.37950.1.1.6.1.6.19.1.3
		priMngStatus OBJECT-TYPE
			SYNTAX INTEGER
				{
				disable(0),
				enable(1)
				}
			MAX-ACCESS read-write
			STATUS current
			DESCRIPTION
				"Description."
			::= { onuPriTr069Manage 3 }

		
--  1.3.6.1.4.1.37950.1.1.6.1.6.19.1.4
		-- 1.3.6.1.4.1.37950.1.1.6.1.6.19.1.4
		priMngAcsAddress OBJECT-TYPE
			SYNTAX OCTET STRING (SIZE (0..128))
			MAX-ACCESS read-write
			STATUS current
			DESCRIPTION
				"Description."
			::= { onuPriTr069Manage 4 }

		
--  1.3.6.1.4.1.37950.1.1.6.1.6.19.1.5
		-- 1.3.6.1.4.1.37950.1.1.6.1.6.19.1.5
		priMngAcsUsername OBJECT-TYPE
			SYNTAX OCTET STRING (SIZE (0..64))
			MAX-ACCESS read-write
			STATUS current
			DESCRIPTION
				"Description."
			::= { onuPriTr069Manage 5 }

		
--  1.3.6.1.4.1.37950.1.1.6.1.6.19.1.6
		-- 1.3.6.1.4.1.37950.1.1.6.1.6.19.1.6
		priMngAcsPassword OBJECT-TYPE
			SYNTAX OCTET STRING (SIZE (0..64))
			MAX-ACCESS read-write
			STATUS current
			DESCRIPTION
				"Description."
			::= { onuPriTr069Manage 6 }

		
--  1.3.6.1.4.1.37950.1.1.6.1.6.19.1.7
		-- 1.3.6.1.4.1.37950.1.1.6.1.6.19.1.7
		priMngCertificateEn OBJECT-TYPE
			SYNTAX INTEGER
				{
				disable(0),
				enable(1)
				}
			MAX-ACCESS read-write
			STATUS current
			DESCRIPTION
				"Description."
			::= { onuPriTr069Manage 7 }

		
--  1.3.6.1.4.1.37950.1.1.6.1.6.19.1.8
		-- 1.3.6.1.4.1.37950.1.1.6.1.6.19.1.8
		priMngInformEn OBJECT-TYPE
			SYNTAX INTEGER
				{
				disable(0),
				enable(1)
				}
			MAX-ACCESS read-write
			STATUS current
			DESCRIPTION
				"Description."
			::= { onuPriTr069Manage 8 }

		
--  1.3.6.1.4.1.37950.1.1.6.1.6.19.1.9
		-- 1.3.6.1.4.1.37950.1.1.6.1.6.19.1.9
		priMngInformIntervalTime OBJECT-TYPE
			SYNTAX Unsigned32 (0..4294967295)
			MAX-ACCESS read-write
			STATUS current
			DESCRIPTION
				"Description."
			::= { onuPriTr069Manage 9 }

		
--  1.3.6.1.4.1.37950.1.1.6.1.6.19.1.10
		-- 1.3.6.1.4.1.37950.1.1.6.1.6.19.1.10
		priMngRevConnUsername OBJECT-TYPE
			SYNTAX OCTET STRING (SIZE (0..64))
			MAX-ACCESS read-write
			STATUS current
			DESCRIPTION
				"Description."
			::= { onuPriTr069Manage 10 }

		
--  1.3.6.1.4.1.37950.1.1.6.1.6.19.1.11
		-- 1.3.6.1.4.1.37950.1.1.6.1.6.19.1.11
		priMngRevConnPassword OBJECT-TYPE
			SYNTAX OCTET STRING (SIZE (0..64))
			MAX-ACCESS read-write
			STATUS current
			DESCRIPTION
				"Description."
			::= { onuPriTr069Manage 11 }

		
--  1.3.6.1.4.1.37950.1.1.6.1.6.19.1.12
		-- 1.3.6.1.4.1.37950.1.1.6.1.6.19.1.12
		priMngAction OBJECT-TYPE
			SYNTAX INTEGER { submit(1) }
			MAX-ACCESS read-write
			STATUS current
			DESCRIPTION
				"Description."
			::= { onuPriTr069Manage 12 }

		
--  1.3.6.1.4.1.37950.1.1.6.1.6.19.1.13
		-- 1.3.6.1.4.1.37950.1.1.6.1.6.19.1.13
		priMngID OBJECT-TYPE
			SYNTAX OCTET STRING
			MAX-ACCESS read-write
			STATUS current
			DESCRIPTION
				"Description."
			::= { onuPriTr069Manage 13 }

		
--  1.3.6.1.4.1.37950.1.1.6.1.6.19.2
		-- 1.3.6.1.4.1.37950.1.1.6.1.6.19.2
		onuPriTr069Stun OBJECT IDENTIFIER ::= { gOnuPriTr069 2 }

		
--  1.3.6.1.4.1.37950.1.1.6.1.6.19.2.1
		-- 1.3.6.1.4.1.37950.1.1.6.1.6.19.2.1
		priStunPonID OBJECT-TYPE
			SYNTAX Integer32
			MAX-ACCESS read-write
			STATUS current
			DESCRIPTION
				"Description."
			::= { onuPriTr069Stun 1 }

		
--  1.3.6.1.4.1.37950.1.1.6.1.6.19.2.2
		-- 1.3.6.1.4.1.37950.1.1.6.1.6.19.2.2
		priStunOnuID OBJECT-TYPE
			SYNTAX Integer32
			MAX-ACCESS read-write
			STATUS current
			DESCRIPTION
				"Description."
			::= { onuPriTr069Stun 2 }

		
--  1.3.6.1.4.1.37950.1.1.6.1.6.19.2.3
		-- 1.3.6.1.4.1.37950.1.1.6.1.6.19.2.3
		priStunStatus OBJECT-TYPE
			SYNTAX INTEGER
				{
				disable(0),
				enable(1)
				}
			MAX-ACCESS read-write
			STATUS current
			DESCRIPTION
				"Description."
			::= { onuPriTr069Stun 3 }

		
--  1.3.6.1.4.1.37950.1.1.6.1.6.19.2.4
		-- 1.3.6.1.4.1.37950.1.1.6.1.6.19.2.4
		priStunAddress OBJECT-TYPE
			SYNTAX OCTET STRING (SIZE (0..128))
			MAX-ACCESS read-write
			STATUS current
			DESCRIPTION
				"Description."
			::= { onuPriTr069Stun 4 }

		
--  1.3.6.1.4.1.37950.1.1.6.1.6.19.2.5
		-- 1.3.6.1.4.1.37950.1.1.6.1.6.19.2.5
		priStunPort OBJECT-TYPE
			SYNTAX Integer32 (1..65535)
			MAX-ACCESS read-write
			STATUS current
			DESCRIPTION
				"Description."
			::= { onuPriTr069Stun 5 }

		
--  1.3.6.1.4.1.37950.1.1.6.1.6.19.2.6
		-- 1.3.6.1.4.1.37950.1.1.6.1.6.19.2.6
		priStunUsername OBJECT-TYPE
			SYNTAX OCTET STRING (SIZE (0..64))
			MAX-ACCESS read-write
			STATUS current
			DESCRIPTION
				"Description."
			::= { onuPriTr069Stun 6 }

		
--  1.3.6.1.4.1.37950.1.1.6.1.6.19.2.7
		-- 1.3.6.1.4.1.37950.1.1.6.1.6.19.2.7
		priStunPassword OBJECT-TYPE
			SYNTAX OCTET STRING (SIZE (0..64))
			MAX-ACCESS read-write
			STATUS current
			DESCRIPTION
				"Description."
			::= { onuPriTr069Stun 7 }

		
--  1.3.6.1.4.1.37950.1.1.6.1.6.19.2.8
		-- 1.3.6.1.4.1.37950.1.1.6.1.6.19.2.8
		priStunAction OBJECT-TYPE
			SYNTAX INTEGER { submit(1) }
			MAX-ACCESS read-write
			STATUS current
			DESCRIPTION
				"Description."
			::= { onuPriTr069Stun 8 }

		
--  1.3.6.1.4.1.37950.1.1.6.1.6.20
		-- 1.3.6.1.4.1.37950.1.1.6.1.6.20
		gOnuPriNatType OBJECT IDENTIFIER ::= { gOnuPriCfg 20 }

		
--  1.3.6.1.4.1.37950.1.1.6.1.6.20.1
		-- 1.3.6.1.4.1.37950.1.1.6.1.6.20.1
		priNatTypePonID OBJECT-TYPE
			SYNTAX Integer32 (1..16)
			MAX-ACCESS read-write
			STATUS current
			DESCRIPTION
				"Description."
			::= { gOnuPriNatType 1 }

		
--  1.3.6.1.4.1.37950.1.1.6.1.6.20.2
		-- 1.3.6.1.4.1.37950.1.1.6.1.6.20.2
		priNatTypeOnuID OBJECT-TYPE
			SYNTAX Integer32 (1..65535)
			MAX-ACCESS read-write
			STATUS current
			DESCRIPTION
				"Description."
			::= { gOnuPriNatType 2 }

		
--  1.3.6.1.4.1.37950.1.1.6.1.6.20.3
		-- 1.3.6.1.4.1.37950.1.1.6.1.6.20.3
		priNatType OBJECT-TYPE
			SYNTAX INTEGER
				{
				nat1(1),
				nat2(2),
				nat3(3),
				nat4-napt(4)
				}
			MAX-ACCESS read-write
			STATUS current
			DESCRIPTION
				"Description."
			::= { gOnuPriNatType 3 }

		
--     1.3.6.1.4.1.37950.1.1.5.12.3.1.7.4
-- 1.3.6.1.4.1.37950.1.1.5.12.3.1.7.4
-- 1.3.6.1.4.1.37950.1.1.5.12.3.1.7.4
-- 1.3.6.1.4.1.37950.1.1.6.1.6.20.4
		-- 1.3.6.1.4.1.37950.1.1.6.1.6.20.4
		priNatTypeAction OBJECT-TYPE
			SYNTAX INTEGER { commit(1) }
			MAX-ACCESS read-write
			STATUS current
			DESCRIPTION
				"Description."
			::= { gOnuPriNatType 4 }

		
--  1.3.6.1.4.1.37950.1.1.6.1.6.21
		-- 1.3.6.1.4.1.37950.1.1.6.1.6.21
		gOnuPriUPnP OBJECT IDENTIFIER ::= { gOnuPriCfg 21 }

		
--  1.3.6.1.4.1.37950.1.1.6.1.6.21.1
		-- 1.3.6.1.4.1.37950.1.1.6.1.6.21.1
		priUpnpPonID OBJECT-TYPE
			SYNTAX Integer32 (1..16)
			MAX-ACCESS read-write
			STATUS current
			DESCRIPTION
				"Description."
			::= { gOnuPriUPnP 1 }

		
--  1.3.6.1.4.1.37950.1.1.6.1.6.21.2
		-- 1.3.6.1.4.1.37950.1.1.6.1.6.21.2
		priUpnpOnuID OBJECT-TYPE
			SYNTAX Integer32 (1..65535)
			MAX-ACCESS read-write
			STATUS current
			DESCRIPTION
				"Description."
			::= { gOnuPriUPnP 2 }

		
--    1.3.6.1.4.1.37950.1.1.5.12.3.1.22.1.8
-- 1.3.6.1.4.1.37950.1.1.5.12.3.1.22.1.8
-- 1.3.6.1.4.1.37950.1.1.6.1.6.21.3
		-- 1.3.6.1.4.1.37950.1.1.6.1.6.21.3
		priUpnpStatus OBJECT-TYPE
			SYNTAX INTEGER
				{
				disable(0),
				enable(1)
				}
			MAX-ACCESS read-write
			STATUS current
			DESCRIPTION
				"Description."
			::= { gOnuPriUPnP 3 }

		
--  1.3.6.1.4.1.37950.1.1.6.1.6.21.4
		-- 1.3.6.1.4.1.37950.1.1.6.1.6.21.4
		priUpnpWanIndex OBJECT-TYPE
			SYNTAX Integer32 (1..8)
			MAX-ACCESS read-write
			STATUS current
			DESCRIPTION
				"Description."
			::= { gOnuPriUPnP 4 }

		
--     1.3.6.1.4.1.37950.1.1.5.12.3.1.7.4
-- 1.3.6.1.4.1.37950.1.1.5.12.3.1.7.4
-- 1.3.6.1.4.1.37950.1.1.5.12.3.1.7.4
-- 1.3.6.1.4.1.37950.1.1.6.1.6.21.5
		-- 1.3.6.1.4.1.37950.1.1.6.1.6.21.5
		priUpnpAction OBJECT-TYPE
			SYNTAX INTEGER { commit(1) }
			MAX-ACCESS read-write
			STATUS current
			DESCRIPTION
				"Description."
			::= { gOnuPriUPnP 5 }

		
--  1.3.6.1.4.1.37950.1.1.6.1.6.22
		-- 1.3.6.1.4.1.37950.1.1.6.1.6.22
		gOnuPriH248Server OBJECT IDENTIFIER ::= { gOnuPriCfg 22 }

		
--  1.3.6.1.4.1.37950.1.1.6.1.6.22.1
		-- 1.3.6.1.4.1.37950.1.1.6.1.6.22.1
		priH248SrvPonID OBJECT-TYPE
			SYNTAX Integer32
			MAX-ACCESS read-write
			STATUS current
			DESCRIPTION
				"Description."
			::= { gOnuPriH248Server 1 }

		
--  1.3.6.1.4.1.37950.1.1.6.1.6.22.2
		-- 1.3.6.1.4.1.37950.1.1.6.1.6.22.2
		priH248SrvOnuID OBJECT-TYPE
			SYNTAX Integer32
			MAX-ACCESS read-write
			STATUS current
			DESCRIPTION
				"Description."
			::= { gOnuPriH248Server 2 }

		
--  1.3.6.1.4.1.37950.1.1.6.1.6.22.3
		-- 1.3.6.1.4.1.37950.1.1.6.1.6.22.3
		priH248SrvMGPort OBJECT-TYPE
			SYNTAX Integer32 (1..65535)
			MAX-ACCESS read-write
			STATUS current
			DESCRIPTION
				"Description."
			DEFVAL { 2944 }
			::= { gOnuPriH248Server 3 }

		
--  1.3.6.1.4.1.37950.1.1.6.1.6.22.4
		-- 1.3.6.1.4.1.37950.1.1.6.1.6.22.4
		priH248SrvMGCServer OBJECT-TYPE
			SYNTAX OCTET STRING (SIZE (1..64))
			MAX-ACCESS read-write
			STATUS current
			DESCRIPTION
				"Description."
			::= { gOnuPriH248Server 4 }

		
--  1.3.6.1.4.1.37950.1.1.6.1.6.22.5
		-- 1.3.6.1.4.1.37950.1.1.6.1.6.22.5
		priH248SrvMGCPort OBJECT-TYPE
			SYNTAX Integer32 (1..65535)
			MAX-ACCESS read-write
			STATUS current
			DESCRIPTION
				"Description."
			DEFVAL { 2944 }
			::= { gOnuPriH248Server 5 }

		
--  1.3.6.1.4.1.37950.1.1.6.1.6.22.6
		-- 1.3.6.1.4.1.37950.1.1.6.1.6.22.6
		priH248SrvBackupMGCServer OBJECT-TYPE
			SYNTAX OCTET STRING (SIZE (0..64))
			MAX-ACCESS read-write
			STATUS current
			DESCRIPTION
				"Description."
			::= { gOnuPriH248Server 6 }

		
--  1.3.6.1.4.1.37950.1.1.6.1.6.22.7
		-- 1.3.6.1.4.1.37950.1.1.6.1.6.22.7
		priH248SrvBackupMGCPort OBJECT-TYPE
			SYNTAX Integer32 (0..65535)
			MAX-ACCESS read-write
			STATUS current
			DESCRIPTION
				"Description."
			::= { gOnuPriH248Server 7 }

		
--  1.3.6.1.4.1.37950.1.1.6.1.6.22.8
		-- 1.3.6.1.4.1.37950.1.1.6.1.6.22.8
		priH248SrvRegisterMode OBJECT-TYPE
			SYNTAX INTEGER
				{
				ip_address(0),
				domain_name(1),
				device_name(2)
				}
			MAX-ACCESS read-write
			STATUS current
			DESCRIPTION
				"Description."
			::= { gOnuPriH248Server 8 }

		
--  1.3.6.1.4.1.37950.1.1.6.1.6.22.9
		-- 1.3.6.1.4.1.37950.1.1.6.1.6.22.9
		priH248SrvMID OBJECT-TYPE
			SYNTAX OCTET STRING (SIZE (0..64))
			MAX-ACCESS read-write
			STATUS current
			DESCRIPTION
				"Description."
			::= { gOnuPriH248Server 9 }

		
--  1.3.6.1.4.1.37950.1.1.6.1.6.22.10
		-- 1.3.6.1.4.1.37950.1.1.6.1.6.22.10
		priH248SrvHeartbeatMode OBJECT-TYPE
			SYNTAX INTEGER
				{
				disable(0),
				active_enable(1),
				passive_enable(2)
				}
			MAX-ACCESS read-write
			STATUS current
			DESCRIPTION
				"Description."
			::= { gOnuPriH248Server 10 }

		
--  1.3.6.1.4.1.37950.1.1.6.1.6.22.11
		-- 1.3.6.1.4.1.37950.1.1.6.1.6.22.11
		priH248SrvHeartbeatFormat OBJECT-TYPE
			SYNTAX INTEGER
				{
				notify(1),
				service_change(2)
				}
			MAX-ACCESS read-write
			STATUS current
			DESCRIPTION
				"Description."
			::= { gOnuPriH248Server 11 }

		
--  1.3.6.1.4.1.37950.1.1.6.1.6.22.12
		-- 1.3.6.1.4.1.37950.1.1.6.1.6.22.12
		priH248SrvHeartbeatCycle OBJECT-TYPE
			SYNTAX Integer32 (1..65535)
			MAX-ACCESS read-write
			STATUS current
			DESCRIPTION
				"Description."
			DEFVAL { 60 }
			::= { gOnuPriH248Server 12 }

		
--  1.3.6.1.4.1.37950.1.1.6.1.6.22.13
		-- 1.3.6.1.4.1.37950.1.1.6.1.6.22.13
		priH248SrvHeartbeatCount OBJECT-TYPE
			SYNTAX Integer32 (1..255)
			MAX-ACCESS read-write
			STATUS current
			DESCRIPTION
				"Description."
			DEFVAL { 3 }
			::= { gOnuPriH248Server 13 }

		
--  1.3.6.1.4.1.37950.1.1.6.1.6.22.14
		-- 1.3.6.1.4.1.37950.1.1.6.1.6.22.14
		priH248SrvAction OBJECT-TYPE
			SYNTAX INTEGER { submit(1) }
			MAX-ACCESS read-write
			STATUS current
			DESCRIPTION
				"Description."
			::= { gOnuPriH248Server 14 }

		
--  1.3.6.1.4.1.37950.1.1.6.1.6.23
		-- 1.3.6.1.4.1.37950.1.1.6.1.6.23
		gOnuPriH248User OBJECT IDENTIFIER ::= { gOnuPriCfg 23 }

		
--  1.3.6.1.4.1.37950.1.1.6.1.6.23.1
		-- 1.3.6.1.4.1.37950.1.1.6.1.6.23.1
		priH248UserPonID OBJECT-TYPE
			SYNTAX Integer32
			MAX-ACCESS read-write
			STATUS current
			DESCRIPTION
				"Description."
			::= { gOnuPriH248User 1 }

		
--  1.3.6.1.4.1.37950.1.1.6.1.6.23.2
		-- 1.3.6.1.4.1.37950.1.1.6.1.6.23.2
		priH248UserOnuID OBJECT-TYPE
			SYNTAX Integer32
			MAX-ACCESS read-write
			STATUS current
			DESCRIPTION
				"Description."
			::= { gOnuPriH248User 2 }

		
--  1.3.6.1.4.1.37950.1.1.6.1.6.23.3
		-- 1.3.6.1.4.1.37950.1.1.6.1.6.23.3
		priH248UserPortIndex OBJECT-TYPE
			SYNTAX Integer32 (1..8)
			MAX-ACCESS read-write
			STATUS current
			DESCRIPTION
				"Description."
			::= { gOnuPriH248User 3 }

		
--  1.3.6.1.4.1.37950.1.1.6.1.6.23.4
		-- 1.3.6.1.4.1.37950.1.1.6.1.6.23.4
		priH248UserName OBJECT-TYPE
			SYNTAX OCTET STRING (SIZE (0..64))
			MAX-ACCESS read-write
			STATUS current
			DESCRIPTION
				"Description."
			::= { gOnuPriH248User 4 }

		
--  1.3.6.1.4.1.37950.1.1.6.1.6.23.5
		-- 1.3.6.1.4.1.37950.1.1.6.1.6.23.5
		priH248UserAction OBJECT-TYPE
			SYNTAX INTEGER { submit(1) }
			MAX-ACCESS read-write
			STATUS current
			DESCRIPTION
				"Description."
			::= { gOnuPriH248User 5 }

		
--  1.3.6.1.4.1.37950.1.1.6.1.6.24
		-- 1.3.6.1.4.1.37950.1.1.6.1.6.24
		gOnuPriH248SignalMediaAlone OBJECT IDENTIFIER ::= { gOnuPriCfg 24 }

		
--  1.3.6.1.4.1.37950.1.1.6.1.6.24.1
		-- 1.3.6.1.4.1.37950.1.1.6.1.6.24.1
		priH248SMAPonID OBJECT-TYPE
			SYNTAX Integer32
			MAX-ACCESS read-write
			STATUS current
			DESCRIPTION
				"Description."
			::= { gOnuPriH248SignalMediaAlone 1 }

		
--  1.3.6.1.4.1.37950.1.1.6.1.6.24.2
		-- 1.3.6.1.4.1.37950.1.1.6.1.6.24.2
		priH248SMAOnuID OBJECT-TYPE
			SYNTAX Integer32
			MAX-ACCESS read-write
			STATUS current
			DESCRIPTION
				"Description."
			::= { gOnuPriH248SignalMediaAlone 2 }

		
--  1.3.6.1.4.1.37950.1.1.6.1.6.24.3
		-- 1.3.6.1.4.1.37950.1.1.6.1.6.24.3
		priH248SMAStatus OBJECT-TYPE
			SYNTAX INTEGER
				{
				disable(0),
				enable(1)
				}
			MAX-ACCESS read-write
			STATUS current
			DESCRIPTION
				"Description."
			::= { gOnuPriH248SignalMediaAlone 3 }

		
--  1.3.6.1.4.1.37950.1.1.6.1.6.24.4
		-- 1.3.6.1.4.1.37950.1.1.6.1.6.24.4
		priH248SMAWanIndex OBJECT-TYPE
			SYNTAX Integer32 (1..8)
			MAX-ACCESS read-write
			STATUS current
			DESCRIPTION
				"Description."
			::= { gOnuPriH248SignalMediaAlone 4 }

		
--  1.3.6.1.4.1.37950.1.1.6.1.6.24.5
		-- 1.3.6.1.4.1.37950.1.1.6.1.6.24.5
		priH248SMAAction OBJECT-TYPE
			SYNTAX INTEGER { submit(1) }
			MAX-ACCESS read-write
			STATUS current
			DESCRIPTION
				"Description."
			::= { gOnuPriH248SignalMediaAlone 5 }

		
--  1.3.6.1.4.1.37950.1.1.6.1.6.25
		-- 1.3.6.1.4.1.37950.1.1.6.1.6.25
		gOnuPriMacAclRule OBJECT IDENTIFIER ::= { gOnuPriCfg 25 }

		
--  1.3.6.1.4.1.37950.1.1.6.1.6.25.1
		-- 1.3.6.1.4.1.37950.1.1.6.1.6.25.1
		priMRulePonID OBJECT-TYPE
			SYNTAX Integer32
			MAX-ACCESS read-write
			STATUS current
			DESCRIPTION
				"Description."
			::= { gOnuPriMacAclRule 1 }

		
--  1.3.6.1.4.1.37950.1.1.6.1.6.25.2
		-- 1.3.6.1.4.1.37950.1.1.6.1.6.25.2
		priMRuleOnuID OBJECT-TYPE
			SYNTAX Integer32
			MAX-ACCESS read-write
			STATUS current
			DESCRIPTION
				"Description."
			::= { gOnuPriMacAclRule 2 }

		
--  1.3.6.1.4.1.37950.1.1.6.1.6.25.3
		-- 1.3.6.1.4.1.37950.1.1.6.1.6.25.3
		priMRuleStatus OBJECT-TYPE
			SYNTAX INTEGER
				{
				disable(0),
				enable(1)
				}
			MAX-ACCESS read-write
			STATUS current
			DESCRIPTION
				"Description."
			::= { gOnuPriMacAclRule 3 }

		
--  1.3.6.1.4.1.37950.1.1.6.1.6.25.4
		-- 1.3.6.1.4.1.37950.1.1.6.1.6.25.4
		priMRuleMode OBJECT-TYPE
			SYNTAX INTEGER { whitelist(0) }
			MAX-ACCESS read-write
			STATUS current
			DESCRIPTION
				"Description."
			::= { gOnuPriMacAclRule 4 }

		
--  1.3.6.1.4.1.37950.1.1.6.1.6.25.5
		-- 1.3.6.1.4.1.37950.1.1.6.1.6.25.5
		priMRuleAction OBJECT-TYPE
			SYNTAX INTEGER { submit(1) }
			MAX-ACCESS read-write
			STATUS current
			DESCRIPTION
				"Description."
			::= { gOnuPriMacAclRule 5 }

		
--  1.3.6.1.4.1.37950.1.1.6.1.6.26
		-- 1.3.6.1.4.1.37950.1.1.6.1.6.26
		gOnuPriMacAclGroup OBJECT IDENTIFIER ::= { gOnuPriCfg 26 }

		
--  1.3.6.1.4.1.37950.1.1.6.1.6.26.1
		-- 1.3.6.1.4.1.37950.1.1.6.1.6.26.1
		priMGroupPonID OBJECT-TYPE
			SYNTAX Integer32
			MAX-ACCESS read-write
			STATUS current
			DESCRIPTION
				"Description."
			::= { gOnuPriMacAclGroup 1 }

		
--  1.3.6.1.4.1.37950.1.1.6.1.6.26.2
		-- 1.3.6.1.4.1.37950.1.1.6.1.6.26.2
		priMGroupOnuID OBJECT-TYPE
			SYNTAX Integer32
			MAX-ACCESS read-write
			STATUS current
			DESCRIPTION
				"Description."
			::= { gOnuPriMacAclGroup 2 }

		
--  1.3.6.1.4.1.37950.1.1.6.1.6.26.3
		-- 1.3.6.1.4.1.37950.1.1.6.1.6.26.3
		priMGroupGroupNum OBJECT-TYPE
			SYNTAX Integer32 (1..32)
			MAX-ACCESS read-write
			STATUS current
			DESCRIPTION
				"Description."
			::= { gOnuPriMacAclGroup 3 }

		
--  1.3.6.1.4.1.37950.1.1.6.1.6.26.4
		-- 1.3.6.1.4.1.37950.1.1.6.1.6.26.4
		priMGroupMAC OBJECT-TYPE
			SYNTAX OCTET STRING
			MAX-ACCESS read-write
			STATUS current
			DESCRIPTION
				"Description."
			::= { gOnuPriMacAclGroup 4 }

		
--  1.3.6.1.4.1.37950.1.1.6.1.6.26.5
		-- 1.3.6.1.4.1.37950.1.1.6.1.6.26.5
		priMGroupMask OBJECT-TYPE
			SYNTAX OCTET STRING
			MAX-ACCESS read-write
			STATUS current
			DESCRIPTION
				"Description."
			::= { gOnuPriMacAclGroup 5 }

		
--  1.3.6.1.4.1.37950.1.1.6.1.6.26.6
		-- 1.3.6.1.4.1.37950.1.1.6.1.6.26.6
		priMGroupAction OBJECT-TYPE
			SYNTAX INTEGER
				{
				add(1),
				delete(2),
				clear(3)
				}
			MAX-ACCESS read-write
			STATUS current
			DESCRIPTION
				"Description."
			::= { gOnuPriMacAclGroup 6 }

		
--  1.3.6.1.4.1.37950.1.1.6.1.6.27
		-- 1.3.6.1.4.1.37950.1.1.6.1.6.27
		gOnuPriMode OBJECT IDENTIFIER ::= { gOnuPriCfg 27 }

		
--  1.3.6.1.4.1.37950.1.1.6.1.6.27.1
		-- 1.3.6.1.4.1.37950.1.1.6.1.6.27.1
		priModePonID OBJECT-TYPE
			SYNTAX Integer32
			MAX-ACCESS read-write
			STATUS current
			DESCRIPTION
				"Description."
			::= { gOnuPriMode 1 }

		
--  1.3.6.1.4.1.37950.1.1.6.1.6.27.2
		-- 1.3.6.1.4.1.37950.1.1.6.1.6.27.2
		priModeOnuID OBJECT-TYPE
			SYNTAX Integer32
			MAX-ACCESS read-write
			STATUS current
			DESCRIPTION
				"Description."
			::= { gOnuPriMode 2 }

		
--  1.3.6.1.4.1.37950.1.1.6.1.6.27.3
		-- 1.3.6.1.4.1.37950.1.1.6.1.6.27.3
		priModeSelectStatus OBJECT-TYPE
			SYNTAX INTEGER
				{
				disable(0),
				enable(1)
				}
			MAX-ACCESS read-write
			STATUS current
			DESCRIPTION
				"Description."
			::= { gOnuPriMode 3 }

		
--  1.3.6.1.4.1.37950.1.1.6.1.6.27.4
		-- 1.3.6.1.4.1.37950.1.1.6.1.6.27.4
		priModeSelect OBJECT-TYPE
			SYNTAX INTEGER
				{
				sfu(0),
				hgu(1),
				auto(2)
				}
			MAX-ACCESS read-write
			STATUS current
			DESCRIPTION
				"Description."
			::= { gOnuPriMode 4 }

		
--  1.3.6.1.4.1.37950.1.1.6.1.6.27.5
		-- 1.3.6.1.4.1.37950.1.1.6.1.6.27.5
		priModeAction OBJECT-TYPE
			SYNTAX INTEGER { submit(1) }
			MAX-ACCESS read-write
			STATUS current
			DESCRIPTION
				"Description."
			::= { gOnuPriMode 5 }

		
--  1.3.6.1.4.1.37950.1.1.6.1.6.28
		-- 1.3.6.1.4.1.37950.1.1.6.1.6.28
		gOnuPriMQTT OBJECT IDENTIFIER ::= { gOnuPriCfg 28 }

		
--  1.3.6.1.4.1.37950.1.1.6.1.6.28.1
		-- 1.3.6.1.4.1.37950.1.1.6.1.6.28.1
		priMQTTPonID OBJECT-TYPE
			SYNTAX Integer32
			MAX-ACCESS read-write
			STATUS current
			DESCRIPTION
				"Description."
			::= { gOnuPriMQTT 1 }

		
--  1.3.6.1.4.1.37950.1.1.6.1.6.28.2
		-- 1.3.6.1.4.1.37950.1.1.6.1.6.28.2
		priMQTTOnuID OBJECT-TYPE
			SYNTAX Integer32
			MAX-ACCESS read-write
			STATUS current
			DESCRIPTION
				"Description."
			::= { gOnuPriMQTT 2 }

		
--  1.3.6.1.4.1.37950.1.1.6.1.6.28.3
		-- 1.3.6.1.4.1.37950.1.1.6.1.6.28.3
		priMQTTEnableStatus OBJECT-TYPE
			SYNTAX INTEGER
				{
				disable(0),
				enable(1)
				}
			MAX-ACCESS read-write
			STATUS current
			DESCRIPTION
				"Description."
			::= { gOnuPriMQTT 3 }

		
--  1.3.6.1.4.1.37950.1.1.6.1.6.28.4
		-- 1.3.6.1.4.1.37950.1.1.6.1.6.28.4
		priMQTTAddress OBJECT-TYPE
			SYNTAX OCTET STRING
			MAX-ACCESS read-write
			STATUS current
			DESCRIPTION
				"Description."
			::= { gOnuPriMQTT 4 }

		
--  1.3.6.1.4.1.37950.1.1.6.1.6.28.5
		-- 1.3.6.1.4.1.37950.1.1.6.1.6.28.5
		priMQTTUserName OBJECT-TYPE
			SYNTAX OCTET STRING
			MAX-ACCESS read-write
			STATUS current
			DESCRIPTION
				"Description."
			::= { gOnuPriMQTT 5 }

		
--  1.3.6.1.4.1.37950.1.1.6.1.6.28.6
		-- 1.3.6.1.4.1.37950.1.1.6.1.6.28.6
		priMQTTPassword OBJECT-TYPE
			SYNTAX OCTET STRING
			MAX-ACCESS read-write
			STATUS current
			DESCRIPTION
				"Description."
			::= { gOnuPriMQTT 6 }

		
--  1.3.6.1.4.1.37950.1.1.6.1.6.28.7
		-- 1.3.6.1.4.1.37950.1.1.6.1.6.28.7
		priMQTTAction OBJECT-TYPE
			SYNTAX INTEGER { submit(1) }
			MAX-ACCESS read-write
			STATUS current
			DESCRIPTION
				"Description."
			::= { gOnuPriMQTT 7 }

		
--  1.3.6.1.4.1.37950.1.1.6.1.6.28.8
		-- 1.3.6.1.4.1.37950.1.1.6.1.6.28.8
		priMQTTID OBJECT-TYPE
			SYNTAX OCTET STRING
			MAX-ACCESS read-write
			STATUS current
			DESCRIPTION
				"Description."
			::= { gOnuPriMQTT 8 }

		
		-- 1.3.6.1.4.1.37950.1.1.6.1.6.29
		gOnuPriAP OBJECT IDENTIFIER ::= { gOnuPriCfg 29 }

		
		-- 1.3.6.1.4.1.37950.1.1.6.1.6.29.1
		priAPPonID OBJECT-TYPE
			SYNTAX Integer32
			MAX-ACCESS read-write
			STATUS current
			DESCRIPTION
				"Description."
			::= { gOnuPriAP 1 }

		
		-- 1.3.6.1.4.1.37950.1.1.6.1.6.29.2
		priAPOnuID OBJECT-TYPE
			SYNTAX Integer32
			MAX-ACCESS read-write
			STATUS current
			DESCRIPTION
				"Description."
			::= { gOnuPriAP 2 }

		
		-- 1.3.6.1.4.1.37950.1.1.6.1.6.29.3
		priAPStatus OBJECT-TYPE
			SYNTAX INTEGER
				{
				disable(0),
				enable(1)
				}
			MAX-ACCESS read-write
			STATUS current
			DESCRIPTION
				"Description."
			::= { gOnuPriAP 3 }

		
		-- 1.3.6.1.4.1.37950.1.1.6.1.6.29.4
		priAPAction OBJECT-TYPE
			SYNTAX INTEGER { submit(1) }
			MAX-ACCESS read-write
			STATUS current
			DESCRIPTION
				"Description."
			::= { gOnuPriAP 4 }

		
		-- 1.3.6.1.4.1.37950.1.1.6.1.6.29.5
		priAPVLAN OBJECT-TYPE
			SYNTAX Integer32 (0..4095)
			MAX-ACCESS read-write
			STATUS current
			DESCRIPTION
				"Description."
			::= { gOnuPriAP 5 }

		
		-- 1.3.6.1.4.1.37950.1.1.6.1.6.30
		gOnuPriEquid OBJECT IDENTIFIER ::= { gOnuPriCfg 30 }

		
		-- 1.3.6.1.4.1.37950.1.1.6.1.6.30.1
		gOnuPriEquidPon OBJECT-TYPE
			SYNTAX Integer32
			MAX-ACCESS read-write
			STATUS current
			DESCRIPTION
				"Description."
			::= { gOnuPriEquid 1 }

		
		-- 1.3.6.1.4.1.37950.1.1.6.1.6.30.2
		gOnuPriEquidOnu OBJECT-TYPE
			SYNTAX Integer32
			MAX-ACCESS read-write
			STATUS current
			DESCRIPTION
				"Description."
			::= { gOnuPriEquid 2 }

		
		-- 1.3.6.1.4.1.37950.1.1.6.1.6.30.3
		gOnuPriEquipmentID OBJECT-TYPE
			SYNTAX OCTET STRING
			MAX-ACCESS read-write
			STATUS current
			DESCRIPTION
				"Description."
			::= { gOnuPriEquid 3 }

		
		-- 1.3.6.1.4.1.37950.1.1.6.1.6.30.4
		gOnuPriEquidAction OBJECT-TYPE
			SYNTAX INTEGER { commit(1) }
			MAX-ACCESS read-write
			STATUS current
			DESCRIPTION
				"Description."
			::= { gOnuPriEquid 4 }

		
--  1.3.6.1.4.1.37950.1.1.6.1.8
		-- 1.3.6.1.4.1.37950.1.1.6.1.8
		gOnuPriCfgInfo OBJECT IDENTIFIER ::= { v1600gOnu 8 }

		
--  1.3.6.1.4.1.37950.1.1.6.1.8.1
		-- 1.3.6.1.4.1.37950.1.1.6.1.8.1
		priOnuInfoTable OBJECT-TYPE
			SYNTAX SEQUENCE OF PriOnuInfoEntry
			MAX-ACCESS not-accessible
			STATUS current
			DESCRIPTION
				"Description."
			::= { gOnuPriCfgInfo 1 }

		
--  1.3.6.1.4.1.37950.1.1.6.1.8.1.1
		-- 1.3.6.1.4.1.37950.1.1.6.1.8.1.1
		priOnuInfoEntry OBJECT-TYPE
			SYNTAX PriOnuInfoEntry
			MAX-ACCESS not-accessible
			STATUS current
			DESCRIPTION
				"Description."
			INDEX { priOnuInfoPonIndx, priOnuInfoOnuIndx }
			::= { priOnuInfoTable 1 }

		
		PriOnuInfoEntry ::=
			SEQUENCE { 
				priOnuInfoPonIndx
					Integer32,
				priOnuInfoOnuIndx
					Integer32,
				priOnuInfoType
					OCTET STRING,
				priOnuInfoSupport
					Unsigned32,
				priOnuInfoOnuMac
					OCTET STRING,
				priOnuInfoCpuUsage
					Integer32,
				priOnuInfoMemoryUsage
					Integer32
			 }

--  1.3.6.1.4.1.37950.1.1.6.1.8.1.1.1
		-- 1.3.6.1.4.1.37950.1.1.6.1.8.1.1.1
		priOnuInfoPonIndx OBJECT-TYPE
			SYNTAX Integer32 (1..16)
			MAX-ACCESS read-write
			STATUS current
			DESCRIPTION
				"Description."
			::= { priOnuInfoEntry 1 }

		
--  1.3.6.1.4.1.37950.1.1.6.1.8.1.1.2
		-- 1.3.6.1.4.1.37950.1.1.6.1.8.1.1.2
		priOnuInfoOnuIndx OBJECT-TYPE
			SYNTAX Integer32 (1..128)
			MAX-ACCESS read-write
			STATUS current
			DESCRIPTION
				"Description."
			::= { priOnuInfoEntry 2 }

		
--  1.3.6.1.4.1.37950.1.1.6.1.8.1.1.3
		-- 1.3.6.1.4.1.37950.1.1.6.1.8.1.1.3
		priOnuInfoType OBJECT-TYPE
			SYNTAX OCTET STRING
			MAX-ACCESS read-write
			STATUS current
			DESCRIPTION
				"Description."
			::= { priOnuInfoEntry 3 }

		
--  1.3.6.1.4.1.37950.1.1.6.1.8.1.1.4
		-- 1.3.6.1.4.1.37950.1.1.6.1.8.1.1.4
		priOnuInfoSupport OBJECT-TYPE
			SYNTAX Unsigned32
			MAX-ACCESS read-write
			STATUS current
			DESCRIPTION
				"Description."
			::= { priOnuInfoEntry 4 }

		
		-- 1.3.6.1.4.1.37950.1.1.6.1.8.1.1.5
		priOnuInfoOnuMac OBJECT-TYPE
			SYNTAX OCTET STRING
			MAX-ACCESS read-write
			STATUS current
			DESCRIPTION
				"Description."
			::= { priOnuInfoEntry 5 }

		
		-- 1.3.6.1.4.1.37950.1.1.6.1.8.1.1.6
		priOnuInfoCpuUsage OBJECT-TYPE
			SYNTAX Integer32
			MAX-ACCESS read-write
			STATUS current
			DESCRIPTION
				"Description."
			::= { priOnuInfoEntry 6 }

		
		-- 1.3.6.1.4.1.37950.1.1.6.1.8.1.1.7
		priOnuInfoMemoryUsage OBJECT-TYPE
			SYNTAX Integer32
			MAX-ACCESS read-write
			STATUS current
			DESCRIPTION
				"Description."
			::= { priOnuInfoEntry 7 }

		
--   1.3.6.1.4.1.37950.1.1.5.12.3.2.9
-- 1.3.6.1.4.1.37950.1.1.6.1.8.2
		-- 1.3.6.1.4.1.37950.1.1.6.1.8.2
		priDhcpServerTable OBJECT-TYPE
			SYNTAX SEQUENCE OF PriDhcpServerEntry
			MAX-ACCESS not-accessible
			STATUS current
			DESCRIPTION
				"Description."
			::= { gOnuPriCfgInfo 2 }

		
--   1.3.6.1.4.1.37950.1.1.5.12.3.2.9.1
-- 1.3.6.1.4.1.37950.1.1.6.1.8.2.1
		-- 1.3.6.1.4.1.37950.1.1.6.1.8.2.1
		priDhcpServerEntry OBJECT-TYPE
			SYNTAX PriDhcpServerEntry
			MAX-ACCESS not-accessible
			STATUS current
			DESCRIPTION
				"Description."
			INDEX { priDhcpServerPon, priDhcpServerOnu }
			::= { priDhcpServerTable 1 }

		
		PriDhcpServerEntry ::=
			SEQUENCE { 
				priDhcpServerPon
					Integer32,
				priDhcpServerOnu
					Integer32,
				priDhcpLanIp
					IpAddress,
				priDhcpLanMask
					IpAddress,
				priDhcpEnable
					INTEGER,
				priDhcpLease
					Unsigned32,
				priDhcpBeginIp
					IpAddress,
				priDhcpEndIp
					IpAddress,
				priDhcpPoolType
					INTEGER,
				priDhcpMasterDns
					IpAddress,
				priDhcpSlaveDns
					IpAddress,
				priDhcpGateway
					IpAddress,
				priDhcpRelayIp
					IpAddress,
				priDhcpDnsMode
					INTEGER
			 }

--   1.3.6.1.4.1.37950.1.1.5.12.3.2.9.1.1
-- 1.3.6.1.4.1.37950.1.1.6.1.8.2.1.1
		-- 1.3.6.1.4.1.37950.1.1.6.1.8.2.1.1
		priDhcpServerPon OBJECT-TYPE
			SYNTAX Integer32 (1..16)
			MAX-ACCESS read-write
			STATUS current
			DESCRIPTION
				"Description."
			::= { priDhcpServerEntry 1 }

		
--   1.3.6.1.4.1.37950.1.1.5.12.3.2.9.1.2
-- 1.3.6.1.4.1.37950.1.1.6.1.8.2.1.2
		-- 1.3.6.1.4.1.37950.1.1.6.1.8.2.1.2
		priDhcpServerOnu OBJECT-TYPE
			SYNTAX Integer32 (1..65535)
			MAX-ACCESS read-write
			STATUS current
			DESCRIPTION
				"Description."
			::= { priDhcpServerEntry 2 }

		
--   1.3.6.1.4.1.37950.1.1.5.12.3.2.9.1.3
-- 1.3.6.1.4.1.37950.1.1.6.1.8.2.1.3
		-- 1.3.6.1.4.1.37950.1.1.6.1.8.2.1.3
		priDhcpLanIp OBJECT-TYPE
			SYNTAX IpAddress
			MAX-ACCESS read-write
			STATUS current
			DESCRIPTION
				"Description."
			::= { priDhcpServerEntry 3 }

		
--   1.3.6.1.4.1.37950.1.1.5.12.3.2.9.1.4
-- 1.3.6.1.4.1.37950.1.1.6.1.8.2.1.4
		-- 1.3.6.1.4.1.37950.1.1.6.1.8.2.1.4
		priDhcpLanMask OBJECT-TYPE
			SYNTAX IpAddress
			MAX-ACCESS read-write
			STATUS current
			DESCRIPTION
				"Description."
			::= { priDhcpServerEntry 4 }

		
--   1.3.6.1.4.1.37950.1.1.5.12.3.2.9.1.5
-- 1.3.6.1.4.1.37950.1.1.6.1.8.2.1.5
		-- 1.3.6.1.4.1.37950.1.1.6.1.8.2.1.5
		priDhcpEnable OBJECT-TYPE
			SYNTAX INTEGER
				{
				disable(0),
				enable(1),
				relay(2)
				}
			MAX-ACCESS read-write
			STATUS current
			DESCRIPTION
				"Description."
			::= { priDhcpServerEntry 5 }

		
--   1.3.6.1.4.1.37950.1.1.5.12.3.2.9.1.6
-- 1.3.6.1.4.1.37950.1.1.6.1.8.2.1.6
		-- 1.3.6.1.4.1.37950.1.1.6.1.8.2.1.6
		priDhcpLease OBJECT-TYPE
			SYNTAX Unsigned32
			MAX-ACCESS read-write
			STATUS current
			DESCRIPTION
				"Description."
			::= { priDhcpServerEntry 6 }

		
--   1.3.6.1.4.1.37950.1.1.5.12.3.2.9.1.7
-- 1.3.6.1.4.1.37950.1.1.6.1.8.2.1.7
		-- 1.3.6.1.4.1.37950.1.1.6.1.8.2.1.7
		priDhcpBeginIp OBJECT-TYPE
			SYNTAX IpAddress
			MAX-ACCESS read-write
			STATUS current
			DESCRIPTION
				"Description."
			::= { priDhcpServerEntry 7 }

		
--   1.3.6.1.4.1.37950.1.1.5.12.3.2.9.1.8
-- 1.3.6.1.4.1.37950.1.1.6.1.8.2.1.8
		-- 1.3.6.1.4.1.37950.1.1.6.1.8.2.1.8
		priDhcpEndIp OBJECT-TYPE
			SYNTAX IpAddress
			MAX-ACCESS read-write
			STATUS current
			DESCRIPTION
				"Description."
			::= { priDhcpServerEntry 8 }

		
--   1.3.6.1.4.1.37950.1.1.5.12.3.2.9.1.9
-- 1.3.6.1.4.1.37950.1.1.6.1.8.2.1.9
		-- 1.3.6.1.4.1.37950.1.1.6.1.8.2.1.9
		priDhcpPoolType OBJECT-TYPE
			SYNTAX INTEGER
				{
				pc(0),
				camera(1),
				stb(2),
				ip_phone(3)
				}
			MAX-ACCESS read-write
			STATUS current
			DESCRIPTION
				"Description."
			::= { priDhcpServerEntry 9 }

		
--   1.3.6.1.4.1.37950.1.1.5.12.3.2.9.1.10
-- 1.3.6.1.4.1.37950.1.1.6.1.8.2.1.10
		-- 1.3.6.1.4.1.37950.1.1.6.1.8.2.1.10
		priDhcpMasterDns OBJECT-TYPE
			SYNTAX IpAddress
			MAX-ACCESS read-write
			STATUS current
			DESCRIPTION
				"Description."
			::= { priDhcpServerEntry 10 }

		
--   1.3.6.1.4.1.37950.1.1.5.12.3.2.9.1.11
-- 1.3.6.1.4.1.37950.1.1.6.1.8.2.1.11
		-- 1.3.6.1.4.1.37950.1.1.6.1.8.2.1.11
		priDhcpSlaveDns OBJECT-TYPE
			SYNTAX IpAddress
			MAX-ACCESS read-write
			STATUS current
			DESCRIPTION
				"Description."
			::= { priDhcpServerEntry 11 }

		
--   1.3.6.1.4.1.37950.1.1.5.12.3.2.9.1.12
-- 1.3.6.1.4.1.37950.1.1.6.1.8.2.1.12
		-- 1.3.6.1.4.1.37950.1.1.6.1.8.2.1.12
		priDhcpGateway OBJECT-TYPE
			SYNTAX IpAddress
			MAX-ACCESS read-write
			STATUS current
			DESCRIPTION
				"Description."
			::= { priDhcpServerEntry 12 }

		
--   1.3.6.1.4.1.37950.1.1.5.12.3.2.9.1.13
-- 1.3.6.1.4.1.37950.1.1.6.1.8.2.1.13
		-- 1.3.6.1.4.1.37950.1.1.6.1.8.2.1.13
		priDhcpRelayIp OBJECT-TYPE
			SYNTAX IpAddress
			MAX-ACCESS read-write
			STATUS current
			DESCRIPTION
				"Description."
			::= { priDhcpServerEntry 13 }

		
--  1.3.6.1.4.1.37950.1.1.6.1.8.2.1.14
		-- 1.3.6.1.4.1.37950.1.1.6.1.8.2.1.14
		priDhcpDnsMode OBJECT-TYPE
			SYNTAX INTEGER
				{
				static(0),
				hgw_proxy(1),
				from_isp(2)
				}
			MAX-ACCESS read-write
			STATUS current
			DESCRIPTION
				"Description."
			::= { priDhcpServerEntry 14 }

		
--   1.3.6.1.4.1.37950.1.1.5.12.3.2.6
-- 1.3.6.1.4.1.37950.1.1.6.1.8.3
		-- 1.3.6.1.4.1.37950.1.1.6.1.8.3
		priWanConnTable OBJECT-TYPE
			SYNTAX SEQUENCE OF PriWanConnEntry
			MAX-ACCESS not-accessible
			STATUS current
			DESCRIPTION
				"Description."
			::= { gOnuPriCfgInfo 3 }

		
--   1.3.6.1.4.1.37950.1.1.5.12.3.2.6.1
-- 1.3.6.1.4.1.37950.1.1.6.1.8.3.1
		-- 1.3.6.1.4.1.37950.1.1.6.1.8.3.1
		priWanConnEntry OBJECT-TYPE
			SYNTAX PriWanConnEntry
			MAX-ACCESS not-accessible
			STATUS current
			DESCRIPTION
				"Description."
			INDEX { priWanConnPonS, priWanConnOnuS, priWanConnIndexS }
			::= { priWanConnTable 1 }

		
		PriWanConnEntry ::=
			SEQUENCE { 
				priWanConnPonS
					INTEGER,
				priWanConnOnuS
					INTEGER,
				priWanConnIndexS
					Integer32,
				priWanConnBindLanS
					INTEGER,
				priWanConnBindSsidS
					INTEGER,
				priWanModeS
					INTEGER,
				priWanConnTypeS
					INTEGER,
				priWanConnVlanIdS
					INTEGER,
				priWanConnVlanCosS
					INTEGER,
				priWanConnNatEnableS
					INTEGER,
				priWanConnModeS
					INTEGER,
				priWanConnIpAddressS
					IpAddress,
				priWanConnIpMaskS
					IpAddress,
				priWanConnGatewayS
					IpAddress,
				priWanConnMasterDns
					IpAddress,
				priWanConnSlaveDns
					IpAddress,
				priWanConnPppoeProxyS
					INTEGER,
				priWanConnPppoeUsernameS
					OCTET STRING,
				priWanConnPppoePasswordS
					OCTET STRING,
				priWanConnPppoeSerName
					OCTET STRING,
				priWanConnPppoeModeS
					INTEGER,
				priWanConnQosEnableS
					INTEGER,
				priWanConnVlanModeS
					INTEGER,
				priWanConnTranslationEnableS
					INTEGER,
				priWanConnTranslationVlanS
					INTEGER,
				priWanConnTranslationCosS
					INTEGER,
				priWanConnQinqEnableS
					INTEGER,
				priWanConnQinqTpidS
					INTEGER,
				priWanConnSvlanIdS
					INTEGER,
				priWanConnSvlanCosS
					INTEGER,
				priWanConnName
					OCTET STRING,
				priWanConnStatus
					INTEGER,
				priWanConnMTU
					Integer32
			 }

--   1.3.6.1.4.1.37950.1.1.5.12.3.2.6.1.1
-- 1.3.6.1.4.1.37950.1.1.6.1.8.3.1.1
		-- 1.3.6.1.4.1.37950.1.1.6.1.8.3.1.1
		priWanConnPonS OBJECT-TYPE
			SYNTAX INTEGER (1..16)
			MAX-ACCESS read-write
			STATUS current
			DESCRIPTION
				"Description."
			::= { priWanConnEntry 1 }

		
--   1.3.6.1.4.1.37950.1.1.5.12.3.2.6.1.2
-- 1.3.6.1.4.1.37950.1.1.6.1.8.3.1.2
		-- 1.3.6.1.4.1.37950.1.1.6.1.8.3.1.2
		priWanConnOnuS OBJECT-TYPE
			SYNTAX INTEGER (1..65535)
			MAX-ACCESS read-write
			STATUS current
			DESCRIPTION
				"Description."
			::= { priWanConnEntry 2 }

		
--   1.3.6.1.4.1.37950.1.1.5.12.3.2.6.1.3
-- 1.3.6.1.4.1.37950.1.1.6.1.8.3.1.3
		-- 1.3.6.1.4.1.37950.1.1.6.1.8.3.1.3
		priWanConnIndexS OBJECT-TYPE
			SYNTAX Integer32 (1..8)
			MAX-ACCESS read-write
			STATUS current
			DESCRIPTION
				"Description."
			::= { priWanConnEntry 3 }

		
--   1.3.6.1.4.1.37950.1.1.5.12.3.2.6.1.4
-- 1.3.6.1.4.1.37950.1.1.6.1.8.3.1.4
		-- 1.3.6.1.4.1.37950.1.1.6.1.8.3.1.4
		priWanConnBindLanS OBJECT-TYPE
			SYNTAX INTEGER (0..255)
			MAX-ACCESS read-write
			STATUS current
			DESCRIPTION
				"Description."
			::= { priWanConnEntry 4 }

		
--   1.3.6.1.4.1.37950.1.1.5.12.3.2.6.1.5
-- 1.3.6.1.4.1.37950.1.1.6.1.8.3.1.5
		-- 1.3.6.1.4.1.37950.1.1.6.1.8.3.1.5
		priWanConnBindSsidS OBJECT-TYPE
			SYNTAX INTEGER (0..255)
			MAX-ACCESS read-write
			STATUS current
			DESCRIPTION
				"Description."
			::= { priWanConnEntry 5 }

		
--   1.3.6.1.4.1.37950.1.1.5.12.3.2.6.1.6
-- 1.3.6.1.4.1.37950.1.1.6.1.8.3.1.6
		-- 1.3.6.1.4.1.37950.1.1.6.1.8.3.1.6
		priWanModeS OBJECT-TYPE
			SYNTAX INTEGER
				{
				internet(0),
				multicast(1),
				tr069(2),
				tr069_internet(3),
				tr069_voip(4),
				voip_internet(5),
				tr069_voip_internet(6),
				voip(7),
				other(100)
				}
			MAX-ACCESS read-write
			STATUS current
			DESCRIPTION
				"Description."
			::= { priWanConnEntry 6 }

		
--   1.3.6.1.4.1.37950.1.1.5.12.3.2.6.1.7
-- 1.3.6.1.4.1.37950.1.1.6.1.8.3.1.7
		-- 1.3.6.1.4.1.37950.1.1.6.1.8.3.1.7
		priWanConnTypeS OBJECT-TYPE
			SYNTAX INTEGER
				{
				bridge(0),
				route(1)
				}
			MAX-ACCESS read-write
			STATUS current
			DESCRIPTION
				"Description."
			::= { priWanConnEntry 7 }

		
--   1.3.6.1.4.1.37950.1.1.5.12.3.2.6.1.8
-- 1.3.6.1.4.1.37950.1.1.6.1.8.3.1.8
		-- 1.3.6.1.4.1.37950.1.1.6.1.8.3.1.8
		priWanConnVlanIdS OBJECT-TYPE
			SYNTAX INTEGER (0..4095)
			MAX-ACCESS read-write
			STATUS current
			DESCRIPTION
				"Description."
			::= { priWanConnEntry 8 }

		
--   1.3.6.1.4.1.37950.1.1.5.12.3.2.6.1.9
-- 1.3.6.1.4.1.37950.1.1.6.1.8.3.1.9
		-- 1.3.6.1.4.1.37950.1.1.6.1.8.3.1.9
		priWanConnVlanCosS OBJECT-TYPE
			SYNTAX INTEGER (0..7)
			MAX-ACCESS read-write
			STATUS current
			DESCRIPTION
				"Description."
			::= { priWanConnEntry 9 }

		
--   1.3.6.1.4.1.37950.1.1.5.12.3.2.6.1.10
-- 1.3.6.1.4.1.37950.1.1.6.1.8.3.1.10
		-- 1.3.6.1.4.1.37950.1.1.6.1.8.3.1.10
		priWanConnNatEnableS OBJECT-TYPE
			SYNTAX INTEGER
				{
				disable(0),
				enable(1)
				}
			MAX-ACCESS read-write
			STATUS current
			DESCRIPTION
				"Description."
			::= { priWanConnEntry 10 }

		
--   1.3.6.1.4.1.37950.1.1.5.12.3.2.6.1.11
-- 1.3.6.1.4.1.37950.1.1.6.1.8.3.1.11
		-- 1.3.6.1.4.1.37950.1.1.6.1.8.3.1.11
		priWanConnModeS OBJECT-TYPE
			SYNTAX INTEGER
				{
				dhcp(0),
				static(1),
				pppoe(2)
				}
			MAX-ACCESS read-write
			STATUS current
			DESCRIPTION
				"Description."
			::= { priWanConnEntry 11 }

		
--   1.3.6.1.4.1.37950.1.1.5.12.3.2.6.1.12
-- 1.3.6.1.4.1.37950.1.1.6.1.8.3.1.12
		-- 1.3.6.1.4.1.37950.1.1.6.1.8.3.1.12
		priWanConnIpAddressS OBJECT-TYPE
			SYNTAX IpAddress
			MAX-ACCESS read-write
			STATUS current
			DESCRIPTION
				"Description."
			::= { priWanConnEntry 12 }

		
--   1.3.6.1.4.1.37950.1.1.5.12.3.2.6.1.13
-- 1.3.6.1.4.1.37950.1.1.6.1.8.3.1.13
		-- 1.3.6.1.4.1.37950.1.1.6.1.8.3.1.13
		priWanConnIpMaskS OBJECT-TYPE
			SYNTAX IpAddress
			MAX-ACCESS read-write
			STATUS current
			DESCRIPTION
				"Description."
			::= { priWanConnEntry 13 }

		
--   1.3.6.1.4.1.37950.1.1.5.12.3.2.6.1.14
-- 1.3.6.1.4.1.37950.1.1.6.1.8.3.1.14
		-- 1.3.6.1.4.1.37950.1.1.6.1.8.3.1.14
		priWanConnGatewayS OBJECT-TYPE
			SYNTAX IpAddress
			MAX-ACCESS read-write
			STATUS current
			DESCRIPTION
				"Description."
			::= { priWanConnEntry 14 }

		
--   1.3.6.1.4.1.37950.1.1.5.12.3.2.6.1.15
-- 1.3.6.1.4.1.37950.1.1.6.1.8.3.1.15
		-- 1.3.6.1.4.1.37950.1.1.6.1.8.3.1.15
		priWanConnMasterDns OBJECT-TYPE
			SYNTAX IpAddress
			MAX-ACCESS read-write
			STATUS current
			DESCRIPTION
				"Description."
			::= { priWanConnEntry 15 }

		
--   1.3.6.1.4.1.37950.1.1.5.12.3.2.6.1.16
-- 1.3.6.1.4.1.37950.1.1.6.1.8.3.1.16
		-- 1.3.6.1.4.1.37950.1.1.6.1.8.3.1.16
		priWanConnSlaveDns OBJECT-TYPE
			SYNTAX IpAddress
			MAX-ACCESS read-write
			STATUS current
			DESCRIPTION
				"Description."
			::= { priWanConnEntry 16 }

		
--   1.3.6.1.4.1.37950.1.1.5.12.3.2.6.1.17
-- 1.3.6.1.4.1.37950.1.1.6.1.8.3.1.17
		-- 1.3.6.1.4.1.37950.1.1.6.1.8.3.1.17
		priWanConnPppoeProxyS OBJECT-TYPE
			SYNTAX INTEGER
				{
				disable(0),
				enable(1)
				}
			MAX-ACCESS read-write
			STATUS current
			DESCRIPTION
				"Description."
			::= { priWanConnEntry 17 }

		
--   1.3.6.1.4.1.37950.1.1.5.12.3.2.6.1.18
-- 1.3.6.1.4.1.37950.1.1.6.1.8.3.1.18
		-- 1.3.6.1.4.1.37950.1.1.6.1.8.3.1.18
		priWanConnPppoeUsernameS OBJECT-TYPE
			SYNTAX OCTET STRING
			MAX-ACCESS read-write
			STATUS current
			DESCRIPTION
				"Description."
			::= { priWanConnEntry 18 }

		
--   1.3.6.1.4.1.37950.1.1.5.12.3.2.6.1.19
-- 1.3.6.1.4.1.37950.1.1.6.1.8.3.1.19
		-- 1.3.6.1.4.1.37950.1.1.6.1.8.3.1.19
		priWanConnPppoePasswordS OBJECT-TYPE
			SYNTAX OCTET STRING
			MAX-ACCESS read-write
			STATUS current
			DESCRIPTION
				"Description."
			::= { priWanConnEntry 19 }

		
--   1.3.6.1.4.1.37950.1.1.5.12.3.2.6.1.20
-- 1.3.6.1.4.1.37950.1.1.6.1.8.3.1.20
		-- 1.3.6.1.4.1.37950.1.1.6.1.8.3.1.20
		priWanConnPppoeSerName OBJECT-TYPE
			SYNTAX OCTET STRING
			MAX-ACCESS read-write
			STATUS current
			DESCRIPTION
				"Description."
			::= { priWanConnEntry 20 }

		
--   1.3.6.1.4.1.37950.1.1.5.12.3.2.6.1.21
-- 1.3.6.1.4.1.37950.1.1.6.1.8.3.1.21
		-- 1.3.6.1.4.1.37950.1.1.6.1.8.3.1.21
		priWanConnPppoeModeS OBJECT-TYPE
			SYNTAX INTEGER
				{
				autoConnect(0),
				connectWhenPayload(1)
				}
			MAX-ACCESS read-write
			STATUS current
			DESCRIPTION
				"Description."
			::= { priWanConnEntry 21 }

		
--   1.3.6.1.4.1.37950.1.1.5.12.3.2.6.1.22
-- 1.3.6.1.4.1.37950.1.1.6.1.8.3.1.22
		-- 1.3.6.1.4.1.37950.1.1.6.1.8.3.1.22
		priWanConnQosEnableS OBJECT-TYPE
			SYNTAX INTEGER
				{
				disable(0),
				enable(1)
				}
			MAX-ACCESS read-write
			STATUS current
			DESCRIPTION
				"Description."
			::= { priWanConnEntry 22 }

		
--   1.3.6.1.4.1.37950.1.1.5.12.3.2.6.1.23
-- 1.3.6.1.4.1.37950.1.1.6.1.8.3.1.23
		-- 1.3.6.1.4.1.37950.1.1.6.1.8.3.1.23
		priWanConnVlanModeS OBJECT-TYPE
			SYNTAX INTEGER
				{
				disable(0),
				tag(1),
				transparent(2)
				}
			MAX-ACCESS read-write
			STATUS current
			DESCRIPTION
				"Description."
			::= { priWanConnEntry 23 }

		
--   1.3.6.1.4.1.37950.1.1.5.12.3.2.6.1.24
-- 1.3.6.1.4.1.37950.1.1.6.1.8.3.1.24
		-- 1.3.6.1.4.1.37950.1.1.6.1.8.3.1.24
		priWanConnTranslationEnableS OBJECT-TYPE
			SYNTAX INTEGER
				{
				disable(0),
				enable(1)
				}
			MAX-ACCESS read-write
			STATUS current
			DESCRIPTION
				"Description."
			::= { priWanConnEntry 24 }

		
--   1.3.6.1.4.1.37950.1.1.5.12.3.2.6.1.25
-- 1.3.6.1.4.1.37950.1.1.6.1.8.3.1.25
		-- 1.3.6.1.4.1.37950.1.1.6.1.8.3.1.25
		priWanConnTranslationVlanS OBJECT-TYPE
			SYNTAX INTEGER (0..4095)
			MAX-ACCESS read-write
			STATUS current
			DESCRIPTION
				"Description."
			::= { priWanConnEntry 25 }

		
--   1.3.6.1.4.1.37950.1.1.5.12.3.2.6.1.26
-- 1.3.6.1.4.1.37950.1.1.6.1.8.3.1.26
		-- 1.3.6.1.4.1.37950.1.1.6.1.8.3.1.26
		priWanConnTranslationCosS OBJECT-TYPE
			SYNTAX INTEGER (0..7)
			MAX-ACCESS read-write
			STATUS current
			DESCRIPTION
				"Description."
			::= { priWanConnEntry 26 }

		
--   1.3.6.1.4.1.37950.1.1.5.12.3.2.6.1.27
-- 1.3.6.1.4.1.37950.1.1.6.1.8.3.1.27
		-- 1.3.6.1.4.1.37950.1.1.6.1.8.3.1.27
		priWanConnQinqEnableS OBJECT-TYPE
			SYNTAX INTEGER
				{
				disable(0),
				enable(1)
				}
			MAX-ACCESS read-write
			STATUS current
			DESCRIPTION
				"Description."
			::= { priWanConnEntry 27 }

		
--   1.3.6.1.4.1.37950.1.1.5.12.3.2.6.1.28
-- 1.3.6.1.4.1.37950.1.1.6.1.8.3.1.28
		-- 1.3.6.1.4.1.37950.1.1.6.1.8.3.1.28
		priWanConnQinqTpidS OBJECT-TYPE
			SYNTAX INTEGER (0..65534)
			MAX-ACCESS read-write
			STATUS current
			DESCRIPTION
				"Description."
			::= { priWanConnEntry 28 }

		
--   1.3.6.1.4.1.37950.1.1.5.12.3.2.6.1.29
-- 1.3.6.1.4.1.37950.1.1.6.1.8.3.1.29
		-- 1.3.6.1.4.1.37950.1.1.6.1.8.3.1.29
		priWanConnSvlanIdS OBJECT-TYPE
			SYNTAX INTEGER (0..4095)
			MAX-ACCESS read-write
			STATUS current
			DESCRIPTION
				"Description."
			::= { priWanConnEntry 29 }

		
--   1.3.6.1.4.1.37950.1.1.5.12.3.2.6.1.30
-- 1.3.6.1.4.1.37950.1.1.6.1.8.3.1.30
		-- 1.3.6.1.4.1.37950.1.1.6.1.8.3.1.30
		priWanConnSvlanCosS OBJECT-TYPE
			SYNTAX INTEGER (0..7)
			MAX-ACCESS read-write
			STATUS current
			DESCRIPTION
				"Description."
			::= { priWanConnEntry 30 }

		
--   1.3.6.1.4.1.37950.1.1.5.12.3.2.6.1.31
-- 1.3.6.1.4.1.37950.1.1.6.1.8.3.1.31
		-- 1.3.6.1.4.1.37950.1.1.6.1.8.3.1.31
		priWanConnName OBJECT-TYPE
			SYNTAX OCTET STRING
			MAX-ACCESS read-write
			STATUS current
			DESCRIPTION
				"Description."
			::= { priWanConnEntry 31 }

		
--   1.3.6.1.4.1.37950.1.1.5.12.3.2.6.1.32
-- 1.3.6.1.4.1.37950.1.1.6.1.8.3.1.32
		-- 1.3.6.1.4.1.37950.1.1.6.1.8.3.1.32
		priWanConnStatus OBJECT-TYPE
			SYNTAX INTEGER
				{
				disconnected(0),
				connected(1)
				}
			MAX-ACCESS read-write
			STATUS current
			DESCRIPTION
				"Description."
			::= { priWanConnEntry 32 }

		
--  1.3.6.1.4.1.37950.1.1.6.1.8.3.1.33
		-- 1.3.6.1.4.1.37950.1.1.6.1.8.3.1.33
		priWanConnMTU OBJECT-TYPE
			SYNTAX Integer32
			MAX-ACCESS read-write
			STATUS current
			DESCRIPTION
				"Description."
			::= { priWanConnEntry 33 }

		
--   1.3.6.1.4.1.37950.1.1.5.12.3.2.4
-- 1.3.6.1.4.1.37950.1.1.6.1.8.4
		-- 1.3.6.1.4.1.37950.1.1.6.1.8.4
		priWifiSwitchTable OBJECT-TYPE
			SYNTAX SEQUENCE OF PriWifiSwitchEntry
			MAX-ACCESS not-accessible
			STATUS current
			DESCRIPTION
				"Description."
			::= { gOnuPriCfgInfo 4 }

		
--   1.3.6.1.4.1.37950.1.1.5.12.3.2.4.1
-- 1.3.6.1.4.1.37950.1.1.6.1.8.4.1
		-- 1.3.6.1.4.1.37950.1.1.6.1.8.4.1
		priWifiSwitchEntry OBJECT-TYPE
			SYNTAX PriWifiSwitchEntry
			MAX-ACCESS not-accessible
			STATUS current
			DESCRIPTION
				"Description."
			INDEX { priWifiSwitchPonS, priWifiSwitchOnuS, priWifiSwitchNoS }
			::= { priWifiSwitchTable 1 }

		
		PriWifiSwitchEntry ::=
			SEQUENCE { 
				priWifiSwitchPonS
					INTEGER,
				priWifiSwitchOnuS
					INTEGER,
				priWifiSwitchNoS
					Integer32,
				priWifiSwitchAPModuleS
					INTEGER,
				priWifiSwitchCountry
					INTEGER,
				priWifiSwitchChannelS
					Integer32,
				priWifiSwitchStandardS
					INTEGER,
				priWifiSwitchPower
					INTEGER,
				priWifiSwitchChannelWidthS
					INTEGER,
				priWifiEasyMeshStatusS
					INTEGER
			 }

--   1.3.6.1.4.1.37950.1.1.5.12.3.2.4.1.1
-- 1.3.6.1.4.1.37950.1.1.6.1.8.4.1.1
		-- 1.3.6.1.4.1.37950.1.1.6.1.8.4.1.1
		priWifiSwitchPonS OBJECT-TYPE
			SYNTAX INTEGER (1..16)
			MAX-ACCESS read-write
			STATUS current
			DESCRIPTION
				"Description."
			::= { priWifiSwitchEntry 1 }

		
--   1.3.6.1.4.1.37950.1.1.5.12.3.2.4.1.2
-- 1.3.6.1.4.1.37950.1.1.6.1.8.4.1.2
		-- 1.3.6.1.4.1.37950.1.1.6.1.8.4.1.2
		priWifiSwitchOnuS OBJECT-TYPE
			SYNTAX INTEGER (1..65535)
			MAX-ACCESS read-write
			STATUS current
			DESCRIPTION
				"Description."
			::= { priWifiSwitchEntry 2 }

		
--  1.3.6.1.4.1.37950.1.1.6.1.8.4.1.3
		-- 1.3.6.1.4.1.37950.1.1.6.1.8.4.1.3
		priWifiSwitchNoS OBJECT-TYPE
			SYNTAX Integer32
			MAX-ACCESS read-write
			STATUS current
			DESCRIPTION
				"Description."
			::= { priWifiSwitchEntry 3 }

		
--   1.3.6.1.4.1.37950.1.1.5.12.3.2.4.1.3
-- 1.3.6.1.4.1.37950.1.1.6.1.8.4.1.4
		-- 1.3.6.1.4.1.37950.1.1.6.1.8.4.1.4
		priWifiSwitchAPModuleS OBJECT-TYPE
			SYNTAX INTEGER
				{
				disable(0),
				enable(1)
				}
			MAX-ACCESS read-write
			STATUS current
			DESCRIPTION
				"Description."
			::= { priWifiSwitchEntry 4 }

		
--   1.3.6.1.4.1.37950.1.1.5.12.3.2.4.1.4
-- 1.3.6.1.4.1.37950.1.1.6.1.8.4.1.5
		-- 1.3.6.1.4.1.37950.1.1.6.1.8.4.1.5
		priWifiSwitchCountry OBJECT-TYPE
			SYNTAX INTEGER
				{
				etsi(0),
				fcc(1),
				ic(2),
				spain(3),
				france(4),
				mkk(5),
				isreal(6),
				mkk2(7),
				mkk3(8),
				russian(9),
				cn(10),
				global(11),
				world-wide(12),
				mkk1(13),
				ncc(14)
				}
			MAX-ACCESS read-write
			STATUS current
			DESCRIPTION
				"Description."
			::= { priWifiSwitchEntry 5 }

		
--   1.3.6.1.4.1.37950.1.1.5.12.3.2.4.1.5
-- 1.3.6.1.4.1.37950.1.1.6.1.8.4.1.6
		-- 1.3.6.1.4.1.37950.1.1.6.1.8.4.1.6
		priWifiSwitchChannelS OBJECT-TYPE
			SYNTAX Integer32
			MAX-ACCESS read-write
			STATUS current
			DESCRIPTION
				"Description."
			::= { priWifiSwitchEntry 6 }

		
--   1.3.6.1.4.1.37950.1.1.5.12.3.2.4.1.6
-- 1.3.6.1.4.1.37950.1.1.6.1.8.4.1.7
		-- 1.3.6.1.4.1.37950.1.1.6.1.8.4.1.7
		priWifiSwitchStandardS OBJECT-TYPE
			SYNTAX INTEGER
				{
				s80211b(0),
				s80211g(1),
				s80211bg(2),
				s80211n(3),
				s80211bgn(4),
				s80211ac(5),
				s80211acA(6),
				s80211acN(7),
				s80211acAN(8),
				s80211acNAC(9),
				s80211acANAC(10),
				s80211acax(11),
				s80211acANACax(12),
				s80211ax(13),
				s80211bgnax(14),
				s80211gn(15)
				}
			MAX-ACCESS read-write
			STATUS current
			DESCRIPTION
				"Description."
			::= { priWifiSwitchEntry 7 }

		
--   1.3.6.1.4.1.37950.1.1.5.12.3.2.4.1.7
-- 1.3.6.1.4.1.37950.1.1.6.1.8.4.1.8
		-- 1.3.6.1.4.1.37950.1.1.6.1.8.4.1.8
		priWifiSwitchPower OBJECT-TYPE
			SYNTAX INTEGER (0..20)
			MAX-ACCESS read-write
			STATUS current
			DESCRIPTION
				"Description."
			::= { priWifiSwitchEntry 8 }

		
--  1.3.6.1.4.1.37950.1.1.6.1.8.4.1.9
		-- 1.3.6.1.4.1.37950.1.1.6.1.8.4.1.9
		priWifiSwitchChannelWidthS OBJECT-TYPE
			SYNTAX INTEGER
				{
				s20MHz(0),
				s40MHz(1),
				s80MHz(2),
				s20_40MHz(3),
				s20_40_80MHz(4),
				s160MHz(5)
				}
			MAX-ACCESS read-write
			STATUS current
			DESCRIPTION
				"Description."
			::= { priWifiSwitchEntry 9 }

		
--  1.3.6.1.4.1.37950.1.1.6.1.8.4.1.10
		-- 1.3.6.1.4.1.37950.1.1.6.1.8.4.1.10
		priWifiEasyMeshStatusS OBJECT-TYPE
			SYNTAX INTEGER
				{
				disable(0),
				enable(1)
				}
			MAX-ACCESS read-write
			STATUS current
			DESCRIPTION
				"Description."
			::= { priWifiSwitchEntry 10 }

		
--   1.3.6.1.4.1.37950.1.1.5.12.3.2.5
-- 1.3.6.1.4.1.37950.1.1.6.1.8.5
		-- 1.3.6.1.4.1.37950.1.1.6.1.8.5
		priWifiSsidTable OBJECT-TYPE
			SYNTAX SEQUENCE OF PriWifiSsidEntry
			MAX-ACCESS not-accessible
			STATUS current
			DESCRIPTION
				"Description."
			::= { gOnuPriCfgInfo 5 }

		
--   1.3.6.1.4.1.37950.1.1.5.12.3.2.5.1
-- 1.3.6.1.4.1.37950.1.1.6.1.8.5.1
		-- 1.3.6.1.4.1.37950.1.1.6.1.8.5.1
		priWifiSsidEntry OBJECT-TYPE
			SYNTAX PriWifiSsidEntry
			MAX-ACCESS not-accessible
			STATUS current
			DESCRIPTION
				"Description."
			INDEX { priWifiSsidPonS, priWifiSsidOnuS, priWifiSsidIdS }
			::= { priWifiSsidTable 1 }

		
		PriWifiSsidEntry ::=
			SEQUENCE { 
				priWifiSsidPonS
					INTEGER,
				priWifiSsidOnuS
					INTEGER,
				priWifiSsidIdS
					Integer32,
				priWifiSsidNameS
					OCTET STRING,
				priWifiSsidEnableS
					INTEGER,
				priWifiSsidHideS
					INTEGER,
				priWifiSsidAuthMode
					INTEGER,
				priWifiSsidEncryTpeS
					INTEGER,
				priSsidPreshareKeyS
					OCTET STRING,
				priSsidWpaRekeyIntervalS
					INTEGER,
				priSsidRadiusServIpTypeS
					INTEGER,
				priSsidRadiusServIp
					OCTET STRING,
				priSsidRadiusServIpPrefixLenS
					INTEGER,
				priSsidRadiusPortS
					INTEGER,
				priSsidRadiusKeyS
					OCTET STRING,
				priSsidWepEncryptionLevelS
					INTEGER,
				priSsidWepKeyIndexS
					INTEGER,
				priSsidWepKey1S
					OCTET STRING,
				priSsidWepKey2S
					OCTET STRING,
				priSsidWepKey3S
					OCTET STRING,
				priSsidWepKey4S
					OCTET STRING
			 }

--   1.3.6.1.4.1.37950.1.1.5.12.3.2.5.1.1
-- 1.3.6.1.4.1.37950.1.1.6.1.8.5.1.1
		-- 1.3.6.1.4.1.37950.1.1.6.1.8.5.1.1
		priWifiSsidPonS OBJECT-TYPE
			SYNTAX INTEGER (1..16)
			MAX-ACCESS read-write
			STATUS current
			DESCRIPTION
				"Description."
			::= { priWifiSsidEntry 1 }

		
--   1.3.6.1.4.1.37950.1.1.5.12.3.2.5.1.2
-- 1.3.6.1.4.1.37950.1.1.6.1.8.5.1.2
		-- 1.3.6.1.4.1.37950.1.1.6.1.8.5.1.2
		priWifiSsidOnuS OBJECT-TYPE
			SYNTAX INTEGER (1..65535)
			MAX-ACCESS read-write
			STATUS current
			DESCRIPTION
				"Description."
			::= { priWifiSsidEntry 2 }

		
--   1.3.6.1.4.1.37950.1.1.5.12.3.2.5.1.3
-- 1.3.6.1.4.1.37950.1.1.6.1.8.5.1.3
		-- 1.3.6.1.4.1.37950.1.1.6.1.8.5.1.3
		priWifiSsidIdS OBJECT-TYPE
			SYNTAX Integer32 (1..10)
			MAX-ACCESS read-write
			STATUS current
			DESCRIPTION
				"Description."
			::= { priWifiSsidEntry 3 }

		
--   1.3.6.1.4.1.37950.1.1.5.12.3.2.5.1.4
-- 1.3.6.1.4.1.37950.1.1.6.1.8.5.1.4
		-- 1.3.6.1.4.1.37950.1.1.6.1.8.5.1.4
		priWifiSsidNameS OBJECT-TYPE
			SYNTAX OCTET STRING
			MAX-ACCESS read-write
			STATUS current
			DESCRIPTION
				"Description."
			::= { priWifiSsidEntry 4 }

		
--   1.3.6.1.4.1.37950.1.1.5.12.3.2.5.1.5
-- 1.3.6.1.4.1.37950.1.1.6.1.8.5.1.5
		-- 1.3.6.1.4.1.37950.1.1.6.1.8.5.1.5
		priWifiSsidEnableS OBJECT-TYPE
			SYNTAX INTEGER
				{
				disable(0),
				enable(1)
				}
			MAX-ACCESS read-write
			STATUS current
			DESCRIPTION
				"Description."
			::= { priWifiSsidEntry 5 }

		
--   1.3.6.1.4.1.37950.1.1.5.12.3.2.5.1.6
-- 1.3.6.1.4.1.37950.1.1.6.1.8.5.1.6
		-- 1.3.6.1.4.1.37950.1.1.6.1.8.5.1.6
		priWifiSsidHideS OBJECT-TYPE
			SYNTAX INTEGER
				{
				disable(0),
				enable(1)
				}
			MAX-ACCESS read-write
			STATUS current
			DESCRIPTION
				"Description."
			::= { priWifiSsidEntry 6 }

		
--   1.3.6.1.4.1.37950.1.1.5.12.3.2.5.1.7
-- 1.3.6.1.4.1.37950.1.1.6.1.8.5.1.7
		-- 1.3.6.1.4.1.37950.1.1.6.1.8.5.1.7
		priWifiSsidAuthMode OBJECT-TYPE
			SYNTAX INTEGER
				{
				open(1),
				shared(2),
				wepauto(3),
				wpapsk(4),
				wpa(5),
				wpa2psk(6),
				wpa2(7),
				wpa_wpa2(8),
				wpapsk_wpa2psk(9),
				wpa3psk(10),
				wpa2psk_wpa3psk(11)
				}
			MAX-ACCESS read-write
			STATUS current
			DESCRIPTION
				"Description."
			::= { priWifiSsidEntry 7 }

		
--   1.3.6.1.4.1.37950.1.1.5.12.3.2.5.1.8
-- 1.3.6.1.4.1.37950.1.1.6.1.8.5.1.8
		-- 1.3.6.1.4.1.37950.1.1.6.1.8.5.1.8
		priWifiSsidEncryTpeS OBJECT-TYPE
			SYNTAX INTEGER
				{
				none(1),
				wep(2),
				tkip(3),
				aes(4),
				tkipaes(5)
				}
			MAX-ACCESS read-write
			STATUS current
			DESCRIPTION
				"Description."
			::= { priWifiSsidEntry 8 }

		
--   1.3.6.1.4.1.37950.1.1.5.12.3.2.5.1.9
-- 1.3.6.1.4.1.37950.1.1.6.1.8.5.1.9
		-- 1.3.6.1.4.1.37950.1.1.6.1.8.5.1.9
		priSsidPreshareKeyS OBJECT-TYPE
			SYNTAX OCTET STRING
			MAX-ACCESS read-write
			STATUS current
			DESCRIPTION
				"Description."
			::= { priWifiSsidEntry 9 }

		
--   1.3.6.1.4.1.37950.1.1.5.12.3.2.5.1.10
-- 1.3.6.1.4.1.37950.1.1.6.1.8.5.1.10
		-- 1.3.6.1.4.1.37950.1.1.6.1.8.5.1.10
		priSsidWpaRekeyIntervalS OBJECT-TYPE
			SYNTAX INTEGER (0..4194303)
			MAX-ACCESS read-write
			STATUS current
			DESCRIPTION
				"Description."
			::= { priWifiSsidEntry 10 }

		
--   1.3.6.1.4.1.37950.1.1.5.12.3.2.5.1.11
-- 1.3.6.1.4.1.37950.1.1.6.1.8.5.1.11
		-- 1.3.6.1.4.1.37950.1.1.6.1.8.5.1.11
		priSsidRadiusServIpTypeS OBJECT-TYPE
			SYNTAX INTEGER
				{
				unknown(0),
				ipv4(1),
				ipv6(2),
				ipv4z(3),
				ipv6z(4),
				dns(16)
				}
			MAX-ACCESS read-write
			STATUS current
			DESCRIPTION
				"Description."
			::= { priWifiSsidEntry 11 }

		
--   1.3.6.1.4.1.37950.1.1.5.12.3.2.5.1.12
-- 1.3.6.1.4.1.37950.1.1.6.1.8.5.1.12
		-- 1.3.6.1.4.1.37950.1.1.6.1.8.5.1.12
		priSsidRadiusServIp OBJECT-TYPE
			SYNTAX OCTET STRING
			MAX-ACCESS read-write
			STATUS current
			DESCRIPTION
				"Description."
			::= { priWifiSsidEntry 12 }

		
--   1.3.6.1.4.1.37950.1.1.5.12.3.2.5.1.13
-- 1.3.6.1.4.1.37950.1.1.6.1.8.5.1.13
		-- 1.3.6.1.4.1.37950.1.1.6.1.8.5.1.13
		priSsidRadiusServIpPrefixLenS OBJECT-TYPE
			SYNTAX INTEGER (0..255)
			MAX-ACCESS read-write
			STATUS current
			DESCRIPTION
				"Description."
			::= { priWifiSsidEntry 13 }

		
--   1.3.6.1.4.1.37950.1.1.5.12.3.2.5.1.14
-- 1.3.6.1.4.1.37950.1.1.6.1.8.5.1.14
		-- 1.3.6.1.4.1.37950.1.1.6.1.8.5.1.14
		priSsidRadiusPortS OBJECT-TYPE
			SYNTAX INTEGER (0..65535)
			MAX-ACCESS read-write
			STATUS current
			DESCRIPTION
				"Description."
			::= { priWifiSsidEntry 14 }

		
--   1.3.6.1.4.1.37950.1.1.5.12.3.2.5.1.15
-- 1.3.6.1.4.1.37950.1.1.6.1.8.5.1.15
		-- 1.3.6.1.4.1.37950.1.1.6.1.8.5.1.15
		priSsidRadiusKeyS OBJECT-TYPE
			SYNTAX OCTET STRING (SIZE (0..32))
			MAX-ACCESS read-write
			STATUS current
			DESCRIPTION
				"Description."
			::= { priWifiSsidEntry 15 }

		
--   1.3.6.1.4.1.37950.1.1.5.12.3.2.5.1.16
-- 1.3.6.1.4.1.37950.1.1.6.1.8.5.1.16
		-- 1.3.6.1.4.1.37950.1.1.6.1.8.5.1.16
		priSsidWepEncryptionLevelS OBJECT-TYPE
			SYNTAX INTEGER
				{
				s64bit(1),
				s128bit(2)
				}
			MAX-ACCESS read-write
			STATUS current
			DESCRIPTION
				"Description."
			::= { priWifiSsidEntry 16 }

		
--   1.3.6.1.4.1.37950.1.1.5.12.3.2.5.1.17
-- 1.3.6.1.4.1.37950.1.1.6.1.8.5.1.17
		-- 1.3.6.1.4.1.37950.1.1.6.1.8.5.1.17
		priSsidWepKeyIndexS OBJECT-TYPE
			SYNTAX INTEGER (1..4)
			MAX-ACCESS read-write
			STATUS current
			DESCRIPTION
				"Description."
			::= { priWifiSsidEntry 17 }

		
--   1.3.6.1.4.1.37950.1.1.5.12.3.2.5.1.18
-- 1.3.6.1.4.1.37950.1.1.6.1.8.5.1.18
		-- 1.3.6.1.4.1.37950.1.1.6.1.8.5.1.18
		priSsidWepKey1S OBJECT-TYPE
			SYNTAX OCTET STRING
			MAX-ACCESS read-write
			STATUS current
			DESCRIPTION
				"Description."
			::= { priWifiSsidEntry 18 }

		
--   1.3.6.1.4.1.37950.1.1.5.12.3.2.5.1.19
-- 1.3.6.1.4.1.37950.1.1.6.1.8.5.1.19
		-- 1.3.6.1.4.1.37950.1.1.6.1.8.5.1.19
		priSsidWepKey2S OBJECT-TYPE
			SYNTAX OCTET STRING
			MAX-ACCESS read-write
			STATUS current
			DESCRIPTION
				"Description."
			::= { priWifiSsidEntry 19 }

		
--   1.3.6.1.4.1.37950.1.1.5.12.3.2.5.1.20
-- 1.3.6.1.4.1.37950.1.1.6.1.8.5.1.20
		-- 1.3.6.1.4.1.37950.1.1.6.1.8.5.1.20
		priSsidWepKey3S OBJECT-TYPE
			SYNTAX OCTET STRING
			MAX-ACCESS read-write
			STATUS current
			DESCRIPTION
				"Description."
			::= { priWifiSsidEntry 20 }

		
--   1.3.6.1.4.1.37950.1.1.5.12.3.2.5.1.21
-- 1.3.6.1.4.1.37950.1.1.6.1.8.5.1.21
		-- 1.3.6.1.4.1.37950.1.1.6.1.8.5.1.21
		priSsidWepKey4S OBJECT-TYPE
			SYNTAX OCTET STRING
			MAX-ACCESS read-write
			STATUS current
			DESCRIPTION
				"Description."
			::= { priWifiSsidEntry 21 }

		
--   1.3.6.1.4.1.37950.1.1.5.12.3.2.14
-- 1.3.6.1.4.1.37950.1.1.6.1.8.6
		-- 1.3.6.1.4.1.37950.1.1.6.1.8.6
		priSipParamTable OBJECT-TYPE
			SYNTAX SEQUENCE OF PriSipParamEntry
			MAX-ACCESS not-accessible
			STATUS current
			DESCRIPTION
				"Description."
			::= { gOnuPriCfgInfo 6 }

		
--   1.3.6.1.4.1.37950.1.1.5.12.3.2.14.1
-- 1.3.6.1.4.1.37950.1.1.6.1.8.6.1
		-- 1.3.6.1.4.1.37950.1.1.6.1.8.6.1
		priSipParamEntry OBJECT-TYPE
			SYNTAX PriSipParamEntry
			MAX-ACCESS not-accessible
			STATUS current
			DESCRIPTION
				"Description."
			INDEX { sipPTPon, sipPTOnu }
			::= { priSipParamTable 1 }

		
		PriSipParamEntry ::=
			SEQUENCE { 
				sipPTPon
					Integer32,
				sipPTOnu
					Integer32,
				sipPTProxyServIp
					OCTET STRING,
				sipPTProxyServPort
					Integer32,
				sipPTBakProxyServIp
					OCTET STRING,
				sipPTBakProxyServPort
					Integer32,
				sipPTRegServIp
					OCTET STRING,
				sipPTRegServPort
					Integer32,
				sipPTBakRegServIp
					OCTET STRING,
				sipPTBakRegServPort
					Integer32,
				sipPTOutBndServIp
					OCTET STRING,
				sipPTOutBndServPort
					Integer32,
				sipPTMgPort
					Integer32,
				sipPTRegInterValue
					Integer32
			 }

--   1.3.6.1.4.1.37950.1.1.5.12.3.2.14.1.1
-- 1.3.6.1.4.1.37950.1.1.6.1.8.6.1.1
		-- 1.3.6.1.4.1.37950.1.1.6.1.8.6.1.1
		sipPTPon OBJECT-TYPE
			SYNTAX Integer32 (1..16)
			MAX-ACCESS read-write
			STATUS current
			DESCRIPTION
				"Description."
			::= { priSipParamEntry 1 }

		
--   1.3.6.1.4.1.37950.1.1.5.12.3.2.14.1.2
-- 1.3.6.1.4.1.37950.1.1.6.1.8.6.1.2
		-- 1.3.6.1.4.1.37950.1.1.6.1.8.6.1.2
		sipPTOnu OBJECT-TYPE
			SYNTAX Integer32 (1..65535)
			MAX-ACCESS read-write
			STATUS current
			DESCRIPTION
				"Description."
			::= { priSipParamEntry 2 }

		
--   1.3.6.1.4.1.37950.1.1.5.12.3.2.14.1.3
-- 1.3.6.1.4.1.37950.1.1.6.1.8.6.1.3
		-- 1.3.6.1.4.1.37950.1.1.6.1.8.6.1.3
		sipPTProxyServIp OBJECT-TYPE
			SYNTAX OCTET STRING
			MAX-ACCESS read-write
			STATUS current
			DESCRIPTION
				"Description."
			::= { priSipParamEntry 3 }

		
--   1.3.6.1.4.1.37950.1.1.5.12.3.2.14.1.4
-- 1.3.6.1.4.1.37950.1.1.6.1.8.6.1.4
		-- 1.3.6.1.4.1.37950.1.1.6.1.8.6.1.4
		sipPTProxyServPort OBJECT-TYPE
			SYNTAX Integer32 (0..65535)
			MAX-ACCESS read-write
			STATUS current
			DESCRIPTION
				"Description."
			::= { priSipParamEntry 4 }

		
--   1.3.6.1.4.1.37950.1.1.5.12.3.2.14.1.5
-- 1.3.6.1.4.1.37950.1.1.6.1.8.6.1.5
		-- 1.3.6.1.4.1.37950.1.1.6.1.8.6.1.5
		sipPTBakProxyServIp OBJECT-TYPE
			SYNTAX OCTET STRING
			MAX-ACCESS read-write
			STATUS current
			DESCRIPTION
				"Description."
			::= { priSipParamEntry 5 }

		
--   1.3.6.1.4.1.37950.1.1.5.12.3.2.14.1.6
-- 1.3.6.1.4.1.37950.1.1.6.1.8.6.1.6
		-- 1.3.6.1.4.1.37950.1.1.6.1.8.6.1.6
		sipPTBakProxyServPort OBJECT-TYPE
			SYNTAX Integer32 (0..65535)
			MAX-ACCESS read-write
			STATUS current
			DESCRIPTION
				"Description."
			::= { priSipParamEntry 6 }

		
--   1.3.6.1.4.1.37950.1.1.5.12.3.2.14.1.7
-- 1.3.6.1.4.1.37950.1.1.6.1.8.6.1.7
		-- 1.3.6.1.4.1.37950.1.1.6.1.8.6.1.7
		sipPTRegServIp OBJECT-TYPE
			SYNTAX OCTET STRING
			MAX-ACCESS read-write
			STATUS current
			DESCRIPTION
				"Description."
			::= { priSipParamEntry 7 }

		
--   1.3.6.1.4.1.37950.1.1.5.12.3.2.14.1.8
-- 1.3.6.1.4.1.37950.1.1.6.1.8.6.1.8
		-- 1.3.6.1.4.1.37950.1.1.6.1.8.6.1.8
		sipPTRegServPort OBJECT-TYPE
			SYNTAX Integer32 (0..65535)
			MAX-ACCESS read-write
			STATUS current
			DESCRIPTION
				"Description."
			::= { priSipParamEntry 8 }

		
--   1.3.6.1.4.1.37950.1.1.5.12.3.2.14.1.9
-- 1.3.6.1.4.1.37950.1.1.6.1.8.6.1.9
		-- 1.3.6.1.4.1.37950.1.1.6.1.8.6.1.9
		sipPTBakRegServIp OBJECT-TYPE
			SYNTAX OCTET STRING
			MAX-ACCESS read-write
			STATUS current
			DESCRIPTION
				"Description."
			::= { priSipParamEntry 9 }

		
--   1.3.6.1.4.1.37950.1.1.5.12.3.2.14.1.10
-- 1.3.6.1.4.1.37950.1.1.6.1.8.6.1.10
		-- 1.3.6.1.4.1.37950.1.1.6.1.8.6.1.10
		sipPTBakRegServPort OBJECT-TYPE
			SYNTAX Integer32 (0..65535)
			MAX-ACCESS read-write
			STATUS current
			DESCRIPTION
				"Description."
			::= { priSipParamEntry 10 }

		
--   1.3.6.1.4.1.37950.1.1.5.12.3.2.14.1.11
-- 1.3.6.1.4.1.37950.1.1.6.1.8.6.1.11
		-- 1.3.6.1.4.1.37950.1.1.6.1.8.6.1.11
		sipPTOutBndServIp OBJECT-TYPE
			SYNTAX OCTET STRING
			MAX-ACCESS read-write
			STATUS current
			DESCRIPTION
				"Description."
			::= { priSipParamEntry 11 }

		
--   1.3.6.1.4.1.37950.1.1.5.12.3.2.14.1.12
-- 1.3.6.1.4.1.37950.1.1.6.1.8.6.1.12
		-- 1.3.6.1.4.1.37950.1.1.6.1.8.6.1.12
		sipPTOutBndServPort OBJECT-TYPE
			SYNTAX Integer32 (0..65535)
			MAX-ACCESS read-write
			STATUS current
			DESCRIPTION
				"Description."
			::= { priSipParamEntry 12 }

		
--   1.3.6.1.4.1.37950.1.1.5.12.3.2.14.1.13
-- 1.3.6.1.4.1.37950.1.1.6.1.8.6.1.13
		-- 1.3.6.1.4.1.37950.1.1.6.1.8.6.1.13
		sipPTMgPort OBJECT-TYPE
			SYNTAX Integer32 (0..65535)
			MAX-ACCESS read-write
			STATUS current
			DESCRIPTION
				"Description."
			::= { priSipParamEntry 13 }

		
--   1.3.6.1.4.1.37950.1.1.5.12.3.2.14.1.15
-- 1.3.6.1.4.1.37950.1.1.6.1.8.6.1.14
		-- 1.3.6.1.4.1.37950.1.1.6.1.8.6.1.14
		sipPTRegInterValue OBJECT-TYPE
			SYNTAX Integer32 (0..10000000)
			MAX-ACCESS read-write
			STATUS current
			DESCRIPTION
				"Description."
			::= { priSipParamEntry 14 }

		
--  1.3.6.1.4.1.37950.1.1.6.1.8.7
		-- 1.3.6.1.4.1.37950.1.1.6.1.8.7
		priSipDigitMapTable OBJECT-TYPE
			SYNTAX SEQUENCE OF PriSipDigitMapEntry
			MAX-ACCESS not-accessible
			STATUS current
			DESCRIPTION
				"Description."
			::= { gOnuPriCfgInfo 7 }

		
--  1.3.6.1.4.1.37950.1.1.6.1.8.7.1
		-- 1.3.6.1.4.1.37950.1.1.6.1.8.7.1
		priSipDigitMapEntry OBJECT-TYPE
			SYNTAX PriSipDigitMapEntry
			MAX-ACCESS not-accessible
			STATUS current
			DESCRIPTION
				"Description."
			INDEX { sipDigitMapPon, sipDigitMapOnu }
			::= { priSipDigitMapTable 1 }

		
		PriSipDigitMapEntry ::=
			SEQUENCE { 
				sipDigitMapPon
					Integer32,
				sipDigitMapOnu
					Integer32,
				sipDigitMapBlock
					OCTET STRING
			 }

--  1.3.6.1.4.1.37950.1.1.6.1.8.7.1.1
		-- 1.3.6.1.4.1.37950.1.1.6.1.8.7.1.1
		sipDigitMapPon OBJECT-TYPE
			SYNTAX Integer32 (1..16)
			MAX-ACCESS read-write
			STATUS current
			DESCRIPTION
				"Description."
			::= { priSipDigitMapEntry 1 }

		
--  1.3.6.1.4.1.37950.1.1.6.1.8.7.1.2
		-- 1.3.6.1.4.1.37950.1.1.6.1.8.7.1.2
		sipDigitMapOnu OBJECT-TYPE
			SYNTAX Integer32 (1..65535)
			MAX-ACCESS read-write
			STATUS current
			DESCRIPTION
				"Description."
			::= { priSipDigitMapEntry 2 }

		
--  1.3.6.1.4.1.37950.1.1.6.1.8.7.1.3
		-- 1.3.6.1.4.1.37950.1.1.6.1.8.7.1.3
		sipDigitMapBlock OBJECT-TYPE
			SYNTAX OCTET STRING
			MAX-ACCESS read-write
			STATUS current
			DESCRIPTION
				"Description."
			::= { priSipDigitMapEntry 3 }

		
--   1.3.6.1.4.1.37950.1.1.5.12.6.1.4.2
-- 1.3.6.1.4.1.37950.1.1.6.1.8.8
		-- 1.3.6.1.4.1.37950.1.1.6.1.8.8
		priSipUserParamTable OBJECT-TYPE
			SYNTAX SEQUENCE OF PriSipUserParamEntry
			MAX-ACCESS not-accessible
			STATUS current
			DESCRIPTION
				"Description."
			::= { gOnuPriCfgInfo 8 }

		
--   1.3.6.1.4.1.37950.1.1.5.12.6.1.4.2.1
-- 1.3.6.1.4.1.37950.1.1.6.1.8.8.1
		-- 1.3.6.1.4.1.37950.1.1.6.1.8.8.1
		priSipUserParamEntry OBJECT-TYPE
			SYNTAX PriSipUserParamEntry
			MAX-ACCESS not-accessible
			STATUS current
			DESCRIPTION
				"Description."
			INDEX { sipUserParamPonNo, sipUserParamOnuNo, sipUserParamPotsNo }
			::= { priSipUserParamTable 1 }

		
		PriSipUserParamEntry ::=
			SEQUENCE { 
				sipUserParamPonNo
					Integer32,
				sipUserParamOnuNo
					Integer32,
				sipUserParamPotsNo
					Integer32,
				sipUserParamUserAccount
					OCTET STRING,
				sipUserParamUserName
					OCTET STRING,
				sipUserParamUserPasswd
					OCTET STRING,
				sipUserParamAccountActive
					INTEGER,
				sipUserParamPortStatus
					OCTET STRING
			 }

--   1.3.6.1.4.1.37950.1.1.5.12.6.1.4.2.1.1
-- 1.3.6.1.4.1.37950.1.1.6.1.8.8.1.1
		-- 1.3.6.1.4.1.37950.1.1.6.1.8.8.1.1
		sipUserParamPonNo OBJECT-TYPE
			SYNTAX Integer32 (1..16)
			MAX-ACCESS read-only
			STATUS current
			DESCRIPTION
				"Description."
			::= { priSipUserParamEntry 1 }

		
--   1.3.6.1.4.1.37950.1.1.5.12.6.1.4.2.1.2
-- 1.3.6.1.4.1.37950.1.1.6.1.8.8.1.2
		-- 1.3.6.1.4.1.37950.1.1.6.1.8.8.1.2
		sipUserParamOnuNo OBJECT-TYPE
			SYNTAX Integer32 (1..65535)
			MAX-ACCESS read-only
			STATUS current
			DESCRIPTION
				"Description."
			::= { priSipUserParamEntry 2 }

		
--   1.3.6.1.4.1.37950.1.1.5.12.6.1.4.2.1.3
-- 1.3.6.1.4.1.37950.1.1.6.1.8.8.1.3
		-- 1.3.6.1.4.1.37950.1.1.6.1.8.8.1.3
		sipUserParamPotsNo OBJECT-TYPE
			SYNTAX Integer32 (0..2)
			MAX-ACCESS read-only
			STATUS current
			DESCRIPTION
				"Description."
			::= { priSipUserParamEntry 3 }

		
--   1.3.6.1.4.1.37950.1.1.5.12.6.1.4.2.1.4
-- 1.3.6.1.4.1.37950.1.1.6.1.8.8.1.4
		-- 1.3.6.1.4.1.37950.1.1.6.1.8.8.1.4
		sipUserParamUserAccount OBJECT-TYPE
			SYNTAX OCTET STRING
			MAX-ACCESS read-only
			STATUS current
			DESCRIPTION
				"Description."
			::= { priSipUserParamEntry 4 }

		
--   1.3.6.1.4.1.37950.1.1.5.12.6.1.4.2.1.5
-- 1.3.6.1.4.1.37950.1.1.6.1.8.8.1.5
		-- 1.3.6.1.4.1.37950.1.1.6.1.8.8.1.5
		sipUserParamUserName OBJECT-TYPE
			SYNTAX OCTET STRING
			MAX-ACCESS read-only
			STATUS current
			DESCRIPTION
				"Description."
			::= { priSipUserParamEntry 5 }

		
--   1.3.6.1.4.1.37950.1.1.5.12.6.1.4.2.1.6
-- 1.3.6.1.4.1.37950.1.1.6.1.8.8.1.6
		-- 1.3.6.1.4.1.37950.1.1.6.1.8.8.1.6
		sipUserParamUserPasswd OBJECT-TYPE
			SYNTAX OCTET STRING
			MAX-ACCESS read-only
			STATUS current
			DESCRIPTION
				"Description."
			::= { priSipUserParamEntry 6 }

		
--  1.3.6.1.4.1.37950.1.1.6.1.8.8.1.7
		-- 1.3.6.1.4.1.37950.1.1.6.1.8.8.1.7
		sipUserParamAccountActive OBJECT-TYPE
			SYNTAX INTEGER
				{
				disable(0),
				enable(1)
				}
			MAX-ACCESS read-write
			STATUS current
			DESCRIPTION
				"Description."
			::= { priSipUserParamEntry 7 }

		
--  1.3.6.1.4.1.37950.1.1.6.1.8.8.1.8
		-- 1.3.6.1.4.1.37950.1.1.6.1.8.8.1.8
		sipUserParamPortStatus OBJECT-TYPE
			SYNTAX OCTET STRING
			MAX-ACCESS read-write
			STATUS current
			DESCRIPTION
				"Description."
			::= { priSipUserParamEntry 8 }

		
--   1.3.6.1.4.1.37950.1.1.5.12.4.2.5
-- 1.3.6.1.4.1.37950.1.1.6.1.8.9
		-- 1.3.6.1.4.1.37950.1.1.6.1.8.9
		priPotsParameterTable OBJECT-TYPE
			SYNTAX SEQUENCE OF PriPotsParameterEntry
			MAX-ACCESS not-accessible
			STATUS current
			DESCRIPTION
				"Description."
			::= { gOnuPriCfgInfo 9 }

		
--   1.3.6.1.4.1.37950.1.1.5.12.4.2.5.1
-- 1.3.6.1.4.1.37950.1.1.6.1.8.9.1
		-- 1.3.6.1.4.1.37950.1.1.6.1.8.9.1
		priPotsParameterEntry OBJECT-TYPE
			SYNTAX PriPotsParameterEntry
			MAX-ACCESS not-accessible
			STATUS current
			DESCRIPTION
				"Description."
			INDEX { priPortPtPonS, priPortPtOnuS, priPortPtPotsNoS }
			::= { priPotsParameterTable 1 }

		
		PriPotsParameterEntry ::=
			SEQUENCE { 
				priPortPtPonS
					Integer32,
				priPortPtOnuS
					Integer32,
				priPortPtPotsNoS
					Integer32,
				priPortPtVarS
					INTEGER,
				priPortPtEchoCancleS
					INTEGER,
				priPotsPtInputGainS
					Integer32,
				priPotsPtOutputGainS
					Integer32,
				priPotsPtDtmfModeS
					INTEGER
			 }

--   1.3.6.1.4.1.37950.1.1.5.12.4.2.5.1.1
-- 1.3.6.1.4.1.37950.1.1.6.1.8.9.1.1
		-- 1.3.6.1.4.1.37950.1.1.6.1.8.9.1.1
		priPortPtPonS OBJECT-TYPE
			SYNTAX Integer32 (1..16)
			MAX-ACCESS read-write
			STATUS current
			DESCRIPTION
				"Description."
			::= { priPotsParameterEntry 1 }

		
--   1.3.6.1.4.1.37950.1.1.5.12.4.2.5.1.2
-- 1.3.6.1.4.1.37950.1.1.6.1.8.9.1.2
		-- 1.3.6.1.4.1.37950.1.1.6.1.8.9.1.2
		priPortPtOnuS OBJECT-TYPE
			SYNTAX Integer32 (1..65535)
			MAX-ACCESS read-write
			STATUS current
			DESCRIPTION
				"Description."
			::= { priPotsParameterEntry 2 }

		
--   1.3.6.1.4.1.37950.1.1.5.12.4.2.5.1.3
-- 1.3.6.1.4.1.37950.1.1.6.1.8.9.1.3
		-- 1.3.6.1.4.1.37950.1.1.6.1.8.9.1.3
		priPortPtPotsNoS OBJECT-TYPE
			SYNTAX Integer32 (1..255)
			MAX-ACCESS read-write
			STATUS current
			DESCRIPTION
				"Description."
			::= { priPotsParameterEntry 3 }

		
--   1.3.6.1.4.1.37950.1.1.5.12.4.2.5.1.4
-- 1.3.6.1.4.1.37950.1.1.6.1.8.9.1.4
		-- 1.3.6.1.4.1.37950.1.1.6.1.8.9.1.4
		priPortPtVarS OBJECT-TYPE
			SYNTAX INTEGER
				{
				disable(0),
				enable(1)
				}
			MAX-ACCESS read-write
			STATUS current
			DESCRIPTION
				"Description."
			::= { priPotsParameterEntry 4 }

		
--   1.3.6.1.4.1.37950.1.1.5.12.4.2.5.1.5
-- 1.3.6.1.4.1.37950.1.1.6.1.8.9.1.5
		-- 1.3.6.1.4.1.37950.1.1.6.1.8.9.1.5
		priPortPtEchoCancleS OBJECT-TYPE
			SYNTAX INTEGER
				{
				disable(0),
				enable(1)
				}
			MAX-ACCESS read-write
			STATUS current
			DESCRIPTION
				"Description."
			::= { priPotsParameterEntry 5 }

		
--   1.3.6.1.4.1.37950.1.1.5.12.4.2.5.1.6
-- 1.3.6.1.4.1.37950.1.1.6.1.8.9.1.6
		-- 1.3.6.1.4.1.37950.1.1.6.1.8.9.1.6
		priPotsPtInputGainS OBJECT-TYPE
			SYNTAX Integer32 (-32..32)
			MAX-ACCESS read-write
			STATUS current
			DESCRIPTION
				"Description."
			::= { priPotsParameterEntry 6 }

		
--   1.3.6.1.4.1.37950.1.1.5.12.4.2.5.1.7
-- 1.3.6.1.4.1.37950.1.1.6.1.8.9.1.7
		-- 1.3.6.1.4.1.37950.1.1.6.1.8.9.1.7
		priPotsPtOutputGainS OBJECT-TYPE
			SYNTAX Integer32 (-32..32)
			MAX-ACCESS read-write
			STATUS current
			DESCRIPTION
				"Description."
			::= { priPotsParameterEntry 7 }

		
--   1.3.6.1.4.1.37950.1.1.5.12.4.2.5.1.8
-- 1.3.6.1.4.1.37950.1.1.6.1.8.9.1.8
		-- 1.3.6.1.4.1.37950.1.1.6.1.8.9.1.8
		priPotsPtDtmfModeS OBJECT-TYPE
			SYNTAX INTEGER
				{
				transparent(0),
				rfc2833(1),
				rfc2833_redundancy(2),
				outband(3)
				}
			MAX-ACCESS read-write
			STATUS current
			DESCRIPTION
				"Description."
			::= { priPotsParameterEntry 8 }

		
--  1.3.6.1.4.1.37950.1.1.6.1.8.10
		-- 1.3.6.1.4.1.37950.1.1.6.1.8.10
		priLanBindModeTable OBJECT-TYPE
			SYNTAX SEQUENCE OF PriLanBindModeEntry
			MAX-ACCESS not-accessible
			STATUS current
			DESCRIPTION
				"Description."
			::= { gOnuPriCfgInfo 10 }

		
--  1.3.6.1.4.1.37950.1.1.6.1.8.10.1
		-- 1.3.6.1.4.1.37950.1.1.6.1.8.10.1
		priLanBindModeEntry OBJECT-TYPE
			SYNTAX PriLanBindModeEntry
			MAX-ACCESS not-accessible
			STATUS current
			DESCRIPTION
				"Description."
			INDEX { priLanBindModePonS, priLanBindModeOnuS, priLanBindModePortIdS }
			::= { priLanBindModeTable 1 }

		
		PriLanBindModeEntry ::=
			SEQUENCE { 
				priLanBindModePonS
					Integer32,
				priLanBindModeOnuS
					Integer32,
				priLanBindModePortIdS
					Integer32,
				priLanBindModeBModeS
					INTEGER,
				priLanBindModeLanVlan1S
					Integer32,
				priLanBindModeWanVlan1S
					Integer32,
				priLanBindModeLanVlan2S
					Integer32,
				priLanBindModeWanVlan2S
					Integer32,
				priLanBindModeLanVlan3S
					Integer32,
				priLanBindModeWanVlan3S
					Integer32,
				priLanBindModeLanVlan4S
					Integer32,
				priLanBindModeWanVlan4S
					Integer32
			 }

--  1.3.6.1.4.1.37950.1.1.6.1.8.10.1.1
		-- 1.3.6.1.4.1.37950.1.1.6.1.8.10.1.1
		priLanBindModePonS OBJECT-TYPE
			SYNTAX Integer32 (1..16)
			MAX-ACCESS read-write
			STATUS current
			DESCRIPTION
				"Description."
			::= { priLanBindModeEntry 1 }

		
--  1.3.6.1.4.1.37950.1.1.6.1.8.10.1.2
		-- 1.3.6.1.4.1.37950.1.1.6.1.8.10.1.2
		priLanBindModeOnuS OBJECT-TYPE
			SYNTAX Integer32 (1..128)
			MAX-ACCESS read-write
			STATUS current
			DESCRIPTION
				"Description."
			::= { priLanBindModeEntry 2 }

		
--  1.3.6.1.4.1.37950.1.1.6.1.8.10.1.3
		-- 1.3.6.1.4.1.37950.1.1.6.1.8.10.1.3
		priLanBindModePortIdS OBJECT-TYPE
			SYNTAX Integer32
			MAX-ACCESS read-write
			STATUS current
			DESCRIPTION
				"Description."
			::= { priLanBindModeEntry 3 }

		
--  1.3.6.1.4.1.37950.1.1.6.1.8.10.1.4
		-- 1.3.6.1.4.1.37950.1.1.6.1.8.10.1.4
		priLanBindModeBModeS OBJECT-TYPE
			SYNTAX INTEGER
				{
				null(0),
				port(1),
				vlan(2)
				}
			MAX-ACCESS read-write
			STATUS current
			DESCRIPTION
				"Description."
			::= { priLanBindModeEntry 4 }

		
--  1.3.6.1.4.1.37950.1.1.6.1.8.10.1.5
		-- 1.3.6.1.4.1.37950.1.1.6.1.8.10.1.5
		priLanBindModeLanVlan1S OBJECT-TYPE
			SYNTAX Integer32
			MAX-ACCESS read-write
			STATUS current
			DESCRIPTION
				"Description."
			::= { priLanBindModeEntry 5 }

		
--  1.3.6.1.4.1.37950.1.1.6.1.8.10.1.6
		-- 1.3.6.1.4.1.37950.1.1.6.1.8.10.1.6
		priLanBindModeWanVlan1S OBJECT-TYPE
			SYNTAX Integer32
			MAX-ACCESS read-write
			STATUS current
			DESCRIPTION
				"Description."
			::= { priLanBindModeEntry 6 }

		
--  1.3.6.1.4.1.37950.1.1.6.1.8.10.1.7
		-- 1.3.6.1.4.1.37950.1.1.6.1.8.10.1.7
		priLanBindModeLanVlan2S OBJECT-TYPE
			SYNTAX Integer32
			MAX-ACCESS read-write
			STATUS current
			DESCRIPTION
				"Description."
			::= { priLanBindModeEntry 7 }

		
--  1.3.6.1.4.1.37950.1.1.6.1.8.10.1.8
		-- 1.3.6.1.4.1.37950.1.1.6.1.8.10.1.8
		priLanBindModeWanVlan2S OBJECT-TYPE
			SYNTAX Integer32
			MAX-ACCESS read-write
			STATUS current
			DESCRIPTION
				"Description."
			::= { priLanBindModeEntry 8 }

		
--  1.3.6.1.4.1.37950.1.1.6.1.8.10.1.9
		-- 1.3.6.1.4.1.37950.1.1.6.1.8.10.1.9
		priLanBindModeLanVlan3S OBJECT-TYPE
			SYNTAX Integer32
			MAX-ACCESS read-write
			STATUS current
			DESCRIPTION
				"Description."
			::= { priLanBindModeEntry 9 }

		
--  1.3.6.1.4.1.37950.1.1.6.1.8.10.1.10
		-- 1.3.6.1.4.1.37950.1.1.6.1.8.10.1.10
		priLanBindModeWanVlan3S OBJECT-TYPE
			SYNTAX Integer32
			MAX-ACCESS read-write
			STATUS current
			DESCRIPTION
				"Description."
			::= { priLanBindModeEntry 10 }

		
--  1.3.6.1.4.1.37950.1.1.6.1.8.10.1.11
		-- 1.3.6.1.4.1.37950.1.1.6.1.8.10.1.11
		priLanBindModeLanVlan4S OBJECT-TYPE
			SYNTAX Integer32
			MAX-ACCESS read-write
			STATUS current
			DESCRIPTION
				"Description."
			::= { priLanBindModeEntry 11 }

		
--  1.3.6.1.4.1.37950.1.1.6.1.8.10.1.12
		-- 1.3.6.1.4.1.37950.1.1.6.1.8.10.1.12
		priLanBindModeWanVlan4S OBJECT-TYPE
			SYNTAX Integer32
			MAX-ACCESS read-write
			STATUS current
			DESCRIPTION
				"Description."
			::= { priLanBindModeEntry 12 }

		
--  1.3.6.1.4.1.37950.1.1.6.1.8.11
		-- 1.3.6.1.4.1.37950.1.1.6.1.8.11
		priMiscCtrlOpTable OBJECT-TYPE
			SYNTAX SEQUENCE OF PriMiscCtrlOpEntry
			MAX-ACCESS not-accessible
			STATUS current
			DESCRIPTION
				"Description."
			::= { gOnuPriCfgInfo 11 }

		
--  1.3.6.1.4.1.37950.1.1.6.1.8.11.1
		-- 1.3.6.1.4.1.37950.1.1.6.1.8.11.1
		priMiscCtrlOpEntry OBJECT-TYPE
			SYNTAX PriMiscCtrlOpEntry
			MAX-ACCESS not-accessible
			STATUS current
			DESCRIPTION
				"Description."
			INDEX { priMiscCtrlOpPonS, priMiscCtrlOpOnuS }
			::= { priMiscCtrlOpTable 1 }

		
		PriMiscCtrlOpEntry ::=
			SEQUENCE { 
				priMiscCtrlOpPonS
					Integer32,
				priMiscCtrlOpOnuS
					Integer32,
				priMiscCtrlOpCatvEnableS
					INTEGER,
				priMiscCtrlOpIgmpEnableS
					INTEGER,
				priMiscCtrlOpStpEnableS
					INTEGER,
				priMiscCtrlOpPortIsoEnableS
					INTEGER,
				priMiscCtrlOpResetButtonS
					INTEGER
			 }

--  1.3.6.1.4.1.37950.1.1.6.1.8.11.1.1
		-- 1.3.6.1.4.1.37950.1.1.6.1.8.11.1.1
		priMiscCtrlOpPonS OBJECT-TYPE
			SYNTAX Integer32 (1..16)
			MAX-ACCESS read-write
			STATUS current
			DESCRIPTION
				"Description."
			::= { priMiscCtrlOpEntry 1 }

		
--  1.3.6.1.4.1.37950.1.1.6.1.8.11.1.2
		-- 1.3.6.1.4.1.37950.1.1.6.1.8.11.1.2
		priMiscCtrlOpOnuS OBJECT-TYPE
			SYNTAX Integer32 (1..128)
			MAX-ACCESS read-write
			STATUS current
			DESCRIPTION
				"Description."
			::= { priMiscCtrlOpEntry 2 }

		
--  1.3.6.1.4.1.37950.1.1.6.1.8.11.1.3
		-- 1.3.6.1.4.1.37950.1.1.6.1.8.11.1.3
		priMiscCtrlOpCatvEnableS OBJECT-TYPE
			SYNTAX INTEGER
				{
				disable(0),
				enable(1)
				}
			MAX-ACCESS read-write
			STATUS current
			DESCRIPTION
				"Description."
			::= { priMiscCtrlOpEntry 3 }

		
--  1.3.6.1.4.1.37950.1.1.6.1.8.11.1.4
		-- 1.3.6.1.4.1.37950.1.1.6.1.8.11.1.4
		priMiscCtrlOpIgmpEnableS OBJECT-TYPE
			SYNTAX INTEGER
				{
				disable(0),
				enable(1)
				}
			MAX-ACCESS read-write
			STATUS current
			DESCRIPTION
				"Description."
			::= { priMiscCtrlOpEntry 4 }

		
--  1.3.6.1.4.1.37950.1.1.6.1.8.11.1.5
		-- 1.3.6.1.4.1.37950.1.1.6.1.8.11.1.5
		priMiscCtrlOpStpEnableS OBJECT-TYPE
			SYNTAX INTEGER
				{
				disable(0),
				enable(1)
				}
			MAX-ACCESS read-write
			STATUS current
			DESCRIPTION
				"Description."
			::= { priMiscCtrlOpEntry 5 }

		
--  1.3.6.1.4.1.37950.1.1.6.1.8.11.1.6
		-- 1.3.6.1.4.1.37950.1.1.6.1.8.11.1.6
		priMiscCtrlOpPortIsoEnableS OBJECT-TYPE
			SYNTAX INTEGER
				{
				disable(0),
				enable(1)
				}
			MAX-ACCESS read-write
			STATUS current
			DESCRIPTION
				"Description."
			::= { priMiscCtrlOpEntry 6 }

		
--  1.3.6.1.4.1.37950.1.1.6.1.8.11.1.7
		-- 1.3.6.1.4.1.37950.1.1.6.1.8.11.1.7
		priMiscCtrlOpResetButtonS OBJECT-TYPE
			SYNTAX INTEGER
				{
				disable(0),
				enable(1)
				}
			MAX-ACCESS read-write
			STATUS current
			DESCRIPTION
				"Description."
			::= { priMiscCtrlOpEntry 7 }

		
--  1.3.6.1.4.1.37950.1.1.6.1.8.12
		-- 1.3.6.1.4.1.37950.1.1.6.1.8.12
		priSpeedLimitTable OBJECT-TYPE
			SYNTAX SEQUENCE OF PriSpeedLimitEntry
			MAX-ACCESS not-accessible
			STATUS current
			DESCRIPTION
				"Description."
			::= { gOnuPriCfgInfo 12 }

		
--  1.3.6.1.4.1.37950.1.1.6.1.8.12.1
		-- 1.3.6.1.4.1.37950.1.1.6.1.8.12.1
		priSpeedLimitEntry OBJECT-TYPE
			SYNTAX PriSpeedLimitEntry
			MAX-ACCESS not-accessible
			STATUS current
			DESCRIPTION
				"Description."
			INDEX { priSpeedLimitPonS, priSpeedLimitOnuS }
			::= { priSpeedLimitTable 1 }

		
		PriSpeedLimitEntry ::=
			SEQUENCE { 
				priSpeedLimitPonS
					Integer32,
				priSpeedLimitOnuS
					Integer32,
				priSpeedLimitUpsLimitS
					Integer32,
				priSpeedLimitDssLimitS
					Integer32
			 }

--  1.3.6.1.4.1.37950.1.1.6.1.8.12.1.1
		-- 1.3.6.1.4.1.37950.1.1.6.1.8.12.1.1
		priSpeedLimitPonS OBJECT-TYPE
			SYNTAX Integer32 (1..16)
			MAX-ACCESS read-write
			STATUS current
			DESCRIPTION
				"Description."
			::= { priSpeedLimitEntry 1 }

		
--  1.3.6.1.4.1.37950.1.1.6.1.8.12.1.2
		-- 1.3.6.1.4.1.37950.1.1.6.1.8.12.1.2
		priSpeedLimitOnuS OBJECT-TYPE
			SYNTAX Integer32 (1..128)
			MAX-ACCESS read-write
			STATUS current
			DESCRIPTION
				"Description."
			::= { priSpeedLimitEntry 2 }

		
--  1.3.6.1.4.1.37950.1.1.6.1.8.12.1.3
		-- 1.3.6.1.4.1.37950.1.1.6.1.8.12.1.3
		priSpeedLimitUpsLimitS OBJECT-TYPE
			SYNTAX Integer32
			MAX-ACCESS read-write
			STATUS current
			DESCRIPTION
				"Description."
			::= { priSpeedLimitEntry 3 }

		
--  1.3.6.1.4.1.37950.1.1.6.1.8.12.1.4
		-- 1.3.6.1.4.1.37950.1.1.6.1.8.12.1.4
		priSpeedLimitDssLimitS OBJECT-TYPE
			SYNTAX Integer32
			MAX-ACCESS read-write
			STATUS current
			DESCRIPTION
				"Description."
			::= { priSpeedLimitEntry 4 }

		
--  1.3.6.1.4.1.37950.1.1.6.1.8.13
		-- 1.3.6.1.4.1.37950.1.1.6.1.8.13
		priMacTableTable OBJECT-TYPE
			SYNTAX SEQUENCE OF PriMacTableEntry
			MAX-ACCESS not-accessible
			STATUS current
			DESCRIPTION
				"Description."
			::= { gOnuPriCfgInfo 13 }

		
--  1.3.6.1.4.1.37950.1.1.6.1.8.13.1
		-- 1.3.6.1.4.1.37950.1.1.6.1.8.13.1
		priMacTableEntry OBJECT-TYPE
			SYNTAX PriMacTableEntry
			MAX-ACCESS not-accessible
			STATUS current
			DESCRIPTION
				"Description."
			INDEX { priMacTablePonS, priMacTableOnus }
			::= { priMacTableTable 1 }

		
		PriMacTableEntry ::=
			SEQUENCE { 
				priMacTablePonS
					Integer32,
				priMacTableOnus
					Integer32,
				priMacTableMacAgingTimeS
					Integer32,
				priMacTablePonMacLimitS
					Integer32,
				priMacTableLanMacLimitSS
					Integer32
			 }

--  1.3.6.1.4.1.37950.1.1.6.1.8.13.1.1
		-- 1.3.6.1.4.1.37950.1.1.6.1.8.13.1.1
		priMacTablePonS OBJECT-TYPE
			SYNTAX Integer32 (1..16)
			MAX-ACCESS read-write
			STATUS current
			DESCRIPTION
				"Description."
			::= { priMacTableEntry 1 }

		
--  1.3.6.1.4.1.37950.1.1.6.1.8.13.1.2
		-- 1.3.6.1.4.1.37950.1.1.6.1.8.13.1.2
		priMacTableOnus OBJECT-TYPE
			SYNTAX Integer32
			MAX-ACCESS read-write
			STATUS current
			DESCRIPTION
				"Description."
			::= { priMacTableEntry 2 }

		
--  1.3.6.1.4.1.37950.1.1.6.1.8.13.1.3
		-- 1.3.6.1.4.1.37950.1.1.6.1.8.13.1.3
		priMacTableMacAgingTimeS OBJECT-TYPE
			SYNTAX Integer32
			MAX-ACCESS read-write
			STATUS current
			DESCRIPTION
				"Description."
			::= { priMacTableEntry 3 }

		
--  1.3.6.1.4.1.37950.1.1.6.1.8.13.1.4
		-- 1.3.6.1.4.1.37950.1.1.6.1.8.13.1.4
		priMacTablePonMacLimitS OBJECT-TYPE
			SYNTAX Integer32
			MAX-ACCESS read-write
			STATUS current
			DESCRIPTION
				"Description."
			::= { priMacTableEntry 4 }

		
--  1.3.6.1.4.1.37950.1.1.6.1.8.13.1.5
		-- 1.3.6.1.4.1.37950.1.1.6.1.8.13.1.5
		priMacTableLanMacLimitSS OBJECT-TYPE
			SYNTAX Integer32
			MAX-ACCESS read-write
			STATUS current
			DESCRIPTION
				"Description."
			::= { priMacTableEntry 5 }

		
--  1.3.6.1.4.1.37950.1.1.6.1.8.14
		-- 1.3.6.1.4.1.37950.1.1.6.1.8.14
		priVoipTable OBJECT-TYPE
			SYNTAX SEQUENCE OF PriVoipEntry
			MAX-ACCESS not-accessible
			STATUS current
			DESCRIPTION
				"Description."
			::= { gOnuPriCfgInfo 14 }

		
--  1.3.6.1.4.1.37950.1.1.6.1.8.14.1
		-- 1.3.6.1.4.1.37950.1.1.6.1.8.14.1
		priVoipEntry OBJECT-TYPE
			SYNTAX PriVoipEntry
			MAX-ACCESS not-accessible
			STATUS current
			DESCRIPTION
				"Description."
			INDEX { priVoipPonS, priVoipOnuS }
			::= { priVoipTable 1 }

		
		PriVoipEntry ::=
			SEQUENCE { 
				priVoipPonS
					Integer32,
				priVoipOnuS
					Integer32,
				priVoipVoiceIPModeS
					OCTET STRING,
				priVoipIPAddress
					IpAddress,
				priVoipNetworkMaskS
					IpAddress,
				priVoipDefaultGatewayS
					IpAddress,
				priVoipPPPOEModeS
					OCTET STRING,
				priVoipPPPOEUserNameS
					OCTET STRING,
				priVoipPPPOEPassWordS
					OCTET STRING,
				priVoipVoiceClientVLANS
					Integer32,
				priVoipVoicePriorityS
					Integer32
			 }

--  1.3.6.1.4.1.37950.1.1.6.1.8.14.1.1
		-- 1.3.6.1.4.1.37950.1.1.6.1.8.14.1.1
		priVoipPonS OBJECT-TYPE
			SYNTAX Integer32
			MAX-ACCESS read-write
			STATUS current
			DESCRIPTION
				"Description."
			::= { priVoipEntry 1 }

		
--  1.3.6.1.4.1.37950.1.1.6.1.8.14.1.2
		-- 1.3.6.1.4.1.37950.1.1.6.1.8.14.1.2
		priVoipOnuS OBJECT-TYPE
			SYNTAX Integer32
			MAX-ACCESS read-write
			STATUS current
			DESCRIPTION
				"Description."
			::= { priVoipEntry 2 }

		
--  1.3.6.1.4.1.37950.1.1.6.1.8.14.1.3
		-- 1.3.6.1.4.1.37950.1.1.6.1.8.14.1.3
		priVoipVoiceIPModeS OBJECT-TYPE
			SYNTAX OCTET STRING
			MAX-ACCESS read-write
			STATUS current
			DESCRIPTION
				"Description."
			::= { priVoipEntry 3 }

		
--  1.3.6.1.4.1.37950.1.1.6.1.8.14.1.4
		-- 1.3.6.1.4.1.37950.1.1.6.1.8.14.1.4
		priVoipIPAddress OBJECT-TYPE
			SYNTAX IpAddress
			MAX-ACCESS read-write
			STATUS current
			DESCRIPTION
				"Description."
			::= { priVoipEntry 4 }

		
--  1.3.6.1.4.1.37950.1.1.6.1.8.14.1.5
		-- 1.3.6.1.4.1.37950.1.1.6.1.8.14.1.5
		priVoipNetworkMaskS OBJECT-TYPE
			SYNTAX IpAddress
			MAX-ACCESS read-write
			STATUS current
			DESCRIPTION
				"Description."
			::= { priVoipEntry 5 }

		
--  1.3.6.1.4.1.37950.1.1.6.1.8.14.1.6
		-- 1.3.6.1.4.1.37950.1.1.6.1.8.14.1.6
		priVoipDefaultGatewayS OBJECT-TYPE
			SYNTAX IpAddress
			MAX-ACCESS read-write
			STATUS current
			DESCRIPTION
				"Description."
			::= { priVoipEntry 6 }

		
--  1.3.6.1.4.1.37950.1.1.6.1.8.14.1.7
		-- 1.3.6.1.4.1.37950.1.1.6.1.8.14.1.7
		priVoipPPPOEModeS OBJECT-TYPE
			SYNTAX OCTET STRING
			MAX-ACCESS read-write
			STATUS current
			DESCRIPTION
				"Description."
			::= { priVoipEntry 7 }

		
--  1.3.6.1.4.1.37950.1.1.6.1.8.14.1.8
		-- 1.3.6.1.4.1.37950.1.1.6.1.8.14.1.8
		priVoipPPPOEUserNameS OBJECT-TYPE
			SYNTAX OCTET STRING
			MAX-ACCESS read-write
			STATUS current
			DESCRIPTION
				"Description."
			::= { priVoipEntry 8 }

		
--  1.3.6.1.4.1.37950.1.1.6.1.8.14.1.9
		-- 1.3.6.1.4.1.37950.1.1.6.1.8.14.1.9
		priVoipPPPOEPassWordS OBJECT-TYPE
			SYNTAX OCTET STRING
			MAX-ACCESS read-write
			STATUS current
			DESCRIPTION
				"Description."
			::= { priVoipEntry 9 }

		
--  1.3.6.1.4.1.37950.1.1.6.1.8.14.1.10
		-- 1.3.6.1.4.1.37950.1.1.6.1.8.14.1.10
		priVoipVoiceClientVLANS OBJECT-TYPE
			SYNTAX Integer32
			MAX-ACCESS read-write
			STATUS current
			DESCRIPTION
				"Description."
			::= { priVoipEntry 10 }

		
--  1.3.6.1.4.1.37950.1.1.6.1.8.14.1.11
		-- 1.3.6.1.4.1.37950.1.1.6.1.8.14.1.11
		priVoipVoicePriorityS OBJECT-TYPE
			SYNTAX Integer32
			MAX-ACCESS read-write
			STATUS current
			DESCRIPTION
				"Description."
			::= { priVoipEntry 11 }

		
--  1.3.6.1.4.1.37950.1.1.6.1.8.15
		-- 1.3.6.1.4.1.37950.1.1.6.1.8.15
		priUsernameTable OBJECT-TYPE
			SYNTAX SEQUENCE OF PriUsernameEntry
			MAX-ACCESS not-accessible
			STATUS current
			DESCRIPTION
				"Description."
			::= { gOnuPriCfgInfo 15 }

		
--  1.3.6.1.4.1.37950.1.1.6.1.8.15.1
		-- 1.3.6.1.4.1.37950.1.1.6.1.8.15.1
		priUsernameEntry OBJECT-TYPE
			SYNTAX PriUsernameEntry
			MAX-ACCESS not-accessible
			STATUS current
			DESCRIPTION
				"Description."
			INDEX { usernamePon, usernameOnu }
			::= { priUsernameTable 1 }

		
		PriUsernameEntry ::=
			SEQUENCE { 
				usernamePon
					Unsigned32,
				usernameOnu
					Unsigned32,
				priUsernameAdminCtl
					INTEGER,
				priUsernameAdminName
					OCTET STRING,
				priUsernameAdminPwd
					OCTET STRING,
				priUsernameUserCtl
					INTEGER,
				priUsernameUserName
					OCTET STRING,
				priUsernameUserPwd
					OCTET STRING
			 }

--  1.3.6.1.4.1.37950.1.1.6.1.8.15.1.1
		-- 1.3.6.1.4.1.37950.1.1.6.1.8.15.1.1
		usernamePon OBJECT-TYPE
			SYNTAX Unsigned32
			MAX-ACCESS read-only
			STATUS current
			DESCRIPTION
				"Description."
			::= { priUsernameEntry 1 }

		
--  1.3.6.1.4.1.37950.1.1.6.1.8.15.1.2
		-- 1.3.6.1.4.1.37950.1.1.6.1.8.15.1.2
		usernameOnu OBJECT-TYPE
			SYNTAX Unsigned32
			MAX-ACCESS read-only
			STATUS current
			DESCRIPTION
				"Description."
			::= { priUsernameEntry 2 }

		
--  1.3.6.1.4.1.37950.1.1.6.1.8.15.1.3
		-- 1.3.6.1.4.1.37950.1.1.6.1.8.15.1.3
		priUsernameAdminCtl OBJECT-TYPE
			SYNTAX INTEGER
				{
				disable(0),
				enable(1)
				}
			MAX-ACCESS read-only
			STATUS current
			DESCRIPTION
				"Description."
			::= { priUsernameEntry 3 }

		
--  1.3.6.1.4.1.37950.1.1.6.1.8.15.1.4
		-- 1.3.6.1.4.1.37950.1.1.6.1.8.15.1.4
		priUsernameAdminName OBJECT-TYPE
			SYNTAX OCTET STRING
			MAX-ACCESS read-only
			STATUS current
			DESCRIPTION
				"Description."
			::= { priUsernameEntry 4 }

		
--  1.3.6.1.4.1.37950.1.1.6.1.8.15.1.5
		-- 1.3.6.1.4.1.37950.1.1.6.1.8.15.1.5
		priUsernameAdminPwd OBJECT-TYPE
			SYNTAX OCTET STRING
			MAX-ACCESS read-only
			STATUS current
			DESCRIPTION
				"Description."
			::= { priUsernameEntry 5 }

		
--  1.3.6.1.4.1.37950.1.1.6.1.8.15.1.6
		-- 1.3.6.1.4.1.37950.1.1.6.1.8.15.1.6
		priUsernameUserCtl OBJECT-TYPE
			SYNTAX INTEGER
				{
				disable(0),
				enable(1)
				}
			MAX-ACCESS read-only
			STATUS current
			DESCRIPTION
				"Description."
			::= { priUsernameEntry 6 }

		
--  1.3.6.1.4.1.37950.1.1.6.1.8.15.1.7
		-- 1.3.6.1.4.1.37950.1.1.6.1.8.15.1.7
		priUsernameUserName OBJECT-TYPE
			SYNTAX OCTET STRING
			MAX-ACCESS read-only
			STATUS current
			DESCRIPTION
				"Description."
			::= { priUsernameEntry 7 }

		
--  1.3.6.1.4.1.37950.1.1.6.1.8.15.1.8
		-- 1.3.6.1.4.1.37950.1.1.6.1.8.15.1.8
		priUsernameUserPwd OBJECT-TYPE
			SYNTAX OCTET STRING
			MAX-ACCESS read-only
			STATUS current
			DESCRIPTION
				"Description."
			::= { priUsernameEntry 8 }

		
--  1.3.6.1.4.1.37950.1.1.6.1.8.16
		-- 1.3.6.1.4.1.37950.1.1.6.1.8.16
		priFirewallTable OBJECT-TYPE
			SYNTAX SEQUENCE OF PriFirewallEntry
			MAX-ACCESS not-accessible
			STATUS current
			DESCRIPTION
				"Description."
			::= { gOnuPriCfgInfo 16 }

		
--  1.3.6.1.4.1.37950.1.1.6.1.8.16.1
		-- 1.3.6.1.4.1.37950.1.1.6.1.8.16.1
		priFirewallEntry OBJECT-TYPE
			SYNTAX PriFirewallEntry
			MAX-ACCESS not-accessible
			STATUS current
			DESCRIPTION
				"Description."
			INDEX { priFirewallPon, priFirewallOnu }
			::= { priFirewallTable 1 }

		
		PriFirewallEntry ::=
			SEQUENCE { 
				priFirewallPon
					Unsigned32,
				priFirewallOnu
					Unsigned32,
				priFirewallLevel
					INTEGER
			 }

--  1.3.6.1.4.1.37950.1.1.6.1.8.16.1.1
		-- 1.3.6.1.4.1.37950.1.1.6.1.8.16.1.1
		priFirewallPon OBJECT-TYPE
			SYNTAX Unsigned32
			MAX-ACCESS read-only
			STATUS current
			DESCRIPTION
				"Description."
			::= { priFirewallEntry 1 }

		
--  1.3.6.1.4.1.37950.1.1.6.1.8.16.1.2
		-- 1.3.6.1.4.1.37950.1.1.6.1.8.16.1.2
		priFirewallOnu OBJECT-TYPE
			SYNTAX Unsigned32
			MAX-ACCESS read-only
			STATUS current
			DESCRIPTION
				"Description."
			::= { priFirewallEntry 2 }

		
--  1.3.6.1.4.1.37950.1.1.6.1.8.16.1.3
		-- 1.3.6.1.4.1.37950.1.1.6.1.8.16.1.3
		priFirewallLevel OBJECT-TYPE
			SYNTAX INTEGER
				{
				disable(0),
				low(1),
				middle(2),
				high(3)
				}
			MAX-ACCESS read-only
			STATUS current
			DESCRIPTION
				"Description."
			::= { priFirewallEntry 3 }

		
--  1.3.6.1.4.1.37950.1.1.6.1.8.17
		-- 1.3.6.1.4.1.37950.1.1.6.1.8.17
		priAclTable OBJECT-TYPE
			SYNTAX SEQUENCE OF PriAclEntry
			MAX-ACCESS not-accessible
			STATUS current
			DESCRIPTION
				"Description."
			::= { gOnuPriCfgInfo 17 }

		
--  1.3.6.1.4.1.37950.1.1.6.1.8.17.1
		-- 1.3.6.1.4.1.37950.1.1.6.1.8.17.1
		priAclEntry OBJECT-TYPE
			SYNTAX PriAclEntry
			MAX-ACCESS not-accessible
			STATUS current
			DESCRIPTION
				"Description."
			INDEX { priAclPon, priAclOnu, priAclProtocolType }
			::= { priAclTable 1 }

		
		PriAclEntry ::=
			SEQUENCE { 
				priAclPon
					Unsigned32,
				priAclOnu
					Unsigned32,
				priAclProtocolType
					INTEGER,
				priAclControl
					INTEGER,
				priAclLanControl
					INTEGER,
				priAclWanControl
					INTEGER,
				priAclIpv4Control
					INTEGER,
				priAclIPv4Address
					IpAddress,
				priAclIPv4MaskAddr
					IpAddress,
				priAclIpv6Control
					INTEGER,
				priAclIPv6Address
					OCTET STRING,
				priAclPort
					Unsigned32
			 }

--  1.3.6.1.4.1.37950.1.1.6.1.8.17.1.1
		-- 1.3.6.1.4.1.37950.1.1.6.1.8.17.1.1
		priAclPon OBJECT-TYPE
			SYNTAX Unsigned32
			MAX-ACCESS read-only
			STATUS current
			DESCRIPTION
				"Description."
			::= { priAclEntry 1 }

		
--  1.3.6.1.4.1.37950.1.1.6.1.8.17.1.2
		-- 1.3.6.1.4.1.37950.1.1.6.1.8.17.1.2
		priAclOnu OBJECT-TYPE
			SYNTAX Unsigned32
			MAX-ACCESS read-only
			STATUS current
			DESCRIPTION
				"Description."
			::= { priAclEntry 2 }

		
--  1.3.6.1.4.1.37950.1.1.6.1.8.17.1.3
		-- 1.3.6.1.4.1.37950.1.1.6.1.8.17.1.3
		priAclProtocolType OBJECT-TYPE
			SYNTAX INTEGER
				{
				ping(0),
				telnet(1),
				ftp(2),
				http(3),
				https(4),
				tftp(5),
				ssh(6)
				}
			MAX-ACCESS read-only
			STATUS current
			DESCRIPTION
				"Description."
			::= { priAclEntry 3 }

		
--  1.3.6.1.4.1.37950.1.1.6.1.8.17.1.4
		-- 1.3.6.1.4.1.37950.1.1.6.1.8.17.1.4
		priAclControl OBJECT-TYPE
			SYNTAX INTEGER
				{
				disable(0),
				enable(1)
				}
			MAX-ACCESS read-write
			STATUS current
			DESCRIPTION
				"Description."
			::= { priAclEntry 4 }

		
--  1.3.6.1.4.1.37950.1.1.6.1.8.17.1.5
		-- 1.3.6.1.4.1.37950.1.1.6.1.8.17.1.5
		priAclLanControl OBJECT-TYPE
			SYNTAX INTEGER
				{
				disable(0),
				enable(1)
				}
			MAX-ACCESS read-write
			STATUS current
			DESCRIPTION
				"Description."
			::= { priAclEntry 5 }

		
--  1.3.6.1.4.1.37950.1.1.6.1.8.17.1.6
		-- 1.3.6.1.4.1.37950.1.1.6.1.8.17.1.6
		priAclWanControl OBJECT-TYPE
			SYNTAX INTEGER
				{
				disable(0),
				enable(1)
				}
			MAX-ACCESS read-write
			STATUS current
			DESCRIPTION
				"Description."
			::= { priAclEntry 6 }

		
--  1.3.6.1.4.1.37950.1.1.6.1.8.17.1.7
		-- 1.3.6.1.4.1.37950.1.1.6.1.8.17.1.7
		priAclIpv4Control OBJECT-TYPE
			SYNTAX INTEGER
				{
				disable(0),
				enable(1)
				}
			MAX-ACCESS read-write
			STATUS current
			DESCRIPTION
				"Description."
			::= { priAclEntry 7 }

		
--  1.3.6.1.4.1.37950.1.1.6.1.8.17.1.8
		-- 1.3.6.1.4.1.37950.1.1.6.1.8.17.1.8
		priAclIPv4Address OBJECT-TYPE
			SYNTAX IpAddress
			MAX-ACCESS read-write
			STATUS current
			DESCRIPTION
				"Description."
			::= { priAclEntry 8 }

		
--  1.3.6.1.4.1.37950.1.1.6.1.8.17.1.9
		-- 1.3.6.1.4.1.37950.1.1.6.1.8.17.1.9
		priAclIPv4MaskAddr OBJECT-TYPE
			SYNTAX IpAddress
			MAX-ACCESS read-write
			STATUS current
			DESCRIPTION
				"Description."
			::= { priAclEntry 9 }

		
--  1.3.6.1.4.1.37950.1.1.6.1.8.17.1.10
		-- 1.3.6.1.4.1.37950.1.1.6.1.8.17.1.10
		priAclIpv6Control OBJECT-TYPE
			SYNTAX INTEGER
				{
				disable(0),
				enable(1)
				}
			MAX-ACCESS read-write
			STATUS current
			DESCRIPTION
				"Description."
			::= { priAclEntry 10 }

		
--  1.3.6.1.4.1.37950.1.1.6.1.8.17.1.11
		-- 1.3.6.1.4.1.37950.1.1.6.1.8.17.1.11
		priAclIPv6Address OBJECT-TYPE
			SYNTAX OCTET STRING
			MAX-ACCESS read-write
			STATUS current
			DESCRIPTION
				"Description."
			::= { priAclEntry 11 }

		
--  1.3.6.1.4.1.37950.1.1.6.1.8.17.1.12
		-- 1.3.6.1.4.1.37950.1.1.6.1.8.17.1.12
		priAclPort OBJECT-TYPE
			SYNTAX Unsigned32 (0..65535)
			MAX-ACCESS read-write
			STATUS current
			DESCRIPTION
				"Description."
			::= { priAclEntry 12 }

		
--  1.3.6.1.4.1.37950.1.1.6.1.8.18
		-- 1.3.6.1.4.1.37950.1.1.6.1.8.18
		priWanConnCfgTable OBJECT-TYPE
			SYNTAX SEQUENCE OF PriWanConnCfgEntry
			MAX-ACCESS not-accessible
			STATUS current
			DESCRIPTION
				"Description."
			::= { gOnuPriCfgInfo 18 }

		
--  1.3.6.1.4.1.37950.1.1.6.1.8.18.1
		-- 1.3.6.1.4.1.37950.1.1.6.1.8.18.1
		priWanConnCfgEntry OBJECT-TYPE
			SYNTAX PriWanConnCfgEntry
			MAX-ACCESS not-accessible
			STATUS current
			DESCRIPTION
				"Description."
			INDEX { priWanConnCfgPonS, priWanConnCfgOnuS, priWanConnCfgIndexS }
			::= { priWanConnCfgTable 1 }

		
		PriWanConnCfgEntry ::=
			SEQUENCE { 
				priWanConnCfgPonS
					INTEGER,
				priWanConnCfgOnuS
					INTEGER,
				priWanConnCfgIndexS
					Integer32,
				priWanConnCfgBindLanS
					INTEGER,
				priWanConnCfgBindSsidS
					INTEGER,
				priWanCfgModeS
					INTEGER,
				priWanConnCfgTypeS
					INTEGER,
				priWanConnCfgVlanIdS
					INTEGER,
				priWanConnCfgVlanCosS
					INTEGER,
				priWanConnCfgNatEnableS
					INTEGER,
				priWanConnCfgModeS
					INTEGER,
				priWanConnCfgIpAddressS
					IpAddress,
				priWanConnCfgIpMaskS
					IpAddress,
				priWanConnCfgGatewayS
					IpAddress,
				priWanConnCfgMasterDns
					IpAddress,
				priWanConnCfgSlaveDns
					IpAddress,
				priWanConnCfgPppoeProxyS
					INTEGER,
				priWanConnCfgPppoeUsernameS
					OCTET STRING,
				priWanConnCfgPppoePasswordS
					OCTET STRING,
				priWanConnCfgPppoeSerName
					OCTET STRING,
				priWanConnCfgPppoeModeS
					INTEGER,
				priWanConnCfgQosEnableS
					INTEGER,
				priWanConnCfgVlanModeS
					INTEGER,
				priWanConnCfgTranslationEnableS
					INTEGER,
				priWanConnCfgTranslationVlanS
					INTEGER,
				priWanConnCfgTranslationCosS
					INTEGER,
				priWanConnCfgQinqEnableS
					INTEGER,
				priWanConnCfgQinqTpidS
					INTEGER,
				priWanConnCfgSvlanIdS
					INTEGER,
				priWanConnCfgSvlanCosS
					INTEGER,
				priWanConnCfgName
					OCTET STRING,
				priWanConnCfgStatus
					INTEGER,
				priWanConnCfgMTU
					Integer32
			 }

--  1.3.6.1.4.1.37950.1.1.6.1.8.18.1.1
		-- 1.3.6.1.4.1.37950.1.1.6.1.8.18.1.1
		priWanConnCfgPonS OBJECT-TYPE
			SYNTAX INTEGER (1..16)
			MAX-ACCESS read-write
			STATUS current
			DESCRIPTION
				"Description."
			::= { priWanConnCfgEntry 1 }

		
--  1.3.6.1.4.1.37950.1.1.6.1.8.18.1.2
		-- 1.3.6.1.4.1.37950.1.1.6.1.8.18.1.2
		priWanConnCfgOnuS OBJECT-TYPE
			SYNTAX INTEGER (1..65535)
			MAX-ACCESS read-write
			STATUS current
			DESCRIPTION
				"Description."
			::= { priWanConnCfgEntry 2 }

		
--  1.3.6.1.4.1.37950.1.1.6.1.8.18.1.3
		-- 1.3.6.1.4.1.37950.1.1.6.1.8.18.1.3
		priWanConnCfgIndexS OBJECT-TYPE
			SYNTAX Integer32 (1..8)
			MAX-ACCESS read-write
			STATUS current
			DESCRIPTION
				"Description."
			::= { priWanConnCfgEntry 3 }

		
--  1.3.6.1.4.1.37950.1.1.6.1.8.18.1.4
		-- 1.3.6.1.4.1.37950.1.1.6.1.8.18.1.4
		priWanConnCfgBindLanS OBJECT-TYPE
			SYNTAX INTEGER (0..255)
			MAX-ACCESS read-write
			STATUS current
			DESCRIPTION
				"Description."
			::= { priWanConnCfgEntry 4 }

		
--  1.3.6.1.4.1.37950.1.1.6.1.8.18.1.5
		-- 1.3.6.1.4.1.37950.1.1.6.1.8.18.1.5
		priWanConnCfgBindSsidS OBJECT-TYPE
			SYNTAX INTEGER (0..255)
			MAX-ACCESS read-write
			STATUS current
			DESCRIPTION
				"Description."
			::= { priWanConnCfgEntry 5 }

		
--  1.3.6.1.4.1.37950.1.1.6.1.8.18.1.6
		-- 1.3.6.1.4.1.37950.1.1.6.1.8.18.1.6
		priWanCfgModeS OBJECT-TYPE
			SYNTAX INTEGER
				{
				internet(0),
				multicast(1),
				tr069(2),
				tr069_internet(3),
				tr069_voip(4),
				voip_internet(5),
				tr069_voip_internet(6),
				voip(7),
				other(100)
				}
			MAX-ACCESS read-write
			STATUS current
			DESCRIPTION
				"Description."
			::= { priWanConnCfgEntry 6 }

		
--  1.3.6.1.4.1.37950.1.1.6.1.8.18.1.7
		-- 1.3.6.1.4.1.37950.1.1.6.1.8.18.1.7
		priWanConnCfgTypeS OBJECT-TYPE
			SYNTAX INTEGER
				{
				bridge(0),
				route(1)
				}
			MAX-ACCESS read-write
			STATUS current
			DESCRIPTION
				"Description."
			::= { priWanConnCfgEntry 7 }

		
--  1.3.6.1.4.1.37950.1.1.6.1.8.18.1.8
		-- 1.3.6.1.4.1.37950.1.1.6.1.8.18.1.8
		priWanConnCfgVlanIdS OBJECT-TYPE
			SYNTAX INTEGER (0..4095)
			MAX-ACCESS read-write
			STATUS current
			DESCRIPTION
				"Description."
			::= { priWanConnCfgEntry 8 }

		
--  1.3.6.1.4.1.37950.1.1.6.1.8.18.1.9
		-- 1.3.6.1.4.1.37950.1.1.6.1.8.18.1.9
		priWanConnCfgVlanCosS OBJECT-TYPE
			SYNTAX INTEGER (0..7)
			MAX-ACCESS read-write
			STATUS current
			DESCRIPTION
				"Description."
			::= { priWanConnCfgEntry 9 }

		
--  1.3.6.1.4.1.37950.1.1.6.1.8.18.1.10
		-- 1.3.6.1.4.1.37950.1.1.6.1.8.18.1.10
		priWanConnCfgNatEnableS OBJECT-TYPE
			SYNTAX INTEGER
				{
				disable(0),
				enable(1)
				}
			MAX-ACCESS read-write
			STATUS current
			DESCRIPTION
				"Description."
			::= { priWanConnCfgEntry 10 }

		
--  1.3.6.1.4.1.37950.1.1.6.1.8.18.1.11
		-- 1.3.6.1.4.1.37950.1.1.6.1.8.18.1.11
		priWanConnCfgModeS OBJECT-TYPE
			SYNTAX INTEGER
				{
				dhcp(0),
				static(1),
				pppoe(2)
				}
			MAX-ACCESS read-write
			STATUS current
			DESCRIPTION
				"Description."
			::= { priWanConnCfgEntry 11 }

		
--  1.3.6.1.4.1.37950.1.1.6.1.8.18.1.12
		-- 1.3.6.1.4.1.37950.1.1.6.1.8.18.1.12
		priWanConnCfgIpAddressS OBJECT-TYPE
			SYNTAX IpAddress
			MAX-ACCESS read-write
			STATUS current
			DESCRIPTION
				"Description."
			::= { priWanConnCfgEntry 12 }

		
--  1.3.6.1.4.1.37950.1.1.6.1.8.18.1.13
		-- 1.3.6.1.4.1.37950.1.1.6.1.8.18.1.13
		priWanConnCfgIpMaskS OBJECT-TYPE
			SYNTAX IpAddress
			MAX-ACCESS read-write
			STATUS current
			DESCRIPTION
				"Description."
			::= { priWanConnCfgEntry 13 }

		
--  1.3.6.1.4.1.37950.1.1.6.1.8.18.1.14
		-- 1.3.6.1.4.1.37950.1.1.6.1.8.18.1.14
		priWanConnCfgGatewayS OBJECT-TYPE
			SYNTAX IpAddress
			MAX-ACCESS read-write
			STATUS current
			DESCRIPTION
				"Description."
			::= { priWanConnCfgEntry 14 }

		
--  1.3.6.1.4.1.37950.1.1.6.1.8.18.1.15
		-- 1.3.6.1.4.1.37950.1.1.6.1.8.18.1.15
		priWanConnCfgMasterDns OBJECT-TYPE
			SYNTAX IpAddress
			MAX-ACCESS read-write
			STATUS current
			DESCRIPTION
				"Description."
			::= { priWanConnCfgEntry 15 }

		
--  1.3.6.1.4.1.37950.1.1.6.1.8.18.1.16
		-- 1.3.6.1.4.1.37950.1.1.6.1.8.18.1.16
		priWanConnCfgSlaveDns OBJECT-TYPE
			SYNTAX IpAddress
			MAX-ACCESS read-write
			STATUS current
			DESCRIPTION
				"Description."
			::= { priWanConnCfgEntry 16 }

		
--  1.3.6.1.4.1.37950.1.1.6.1.8.18.1.17
		-- 1.3.6.1.4.1.37950.1.1.6.1.8.18.1.17
		priWanConnCfgPppoeProxyS OBJECT-TYPE
			SYNTAX INTEGER
				{
				disable(0),
				enable(1)
				}
			MAX-ACCESS read-write
			STATUS current
			DESCRIPTION
				"Description."
			::= { priWanConnCfgEntry 17 }

		
--  1.3.6.1.4.1.37950.1.1.6.1.8.18.1.18
		-- 1.3.6.1.4.1.37950.1.1.6.1.8.18.1.18
		priWanConnCfgPppoeUsernameS OBJECT-TYPE
			SYNTAX OCTET STRING
			MAX-ACCESS read-write
			STATUS current
			DESCRIPTION
				"Description."
			::= { priWanConnCfgEntry 18 }

		
--  1.3.6.1.4.1.37950.1.1.6.1.8.18.1.19
		-- 1.3.6.1.4.1.37950.1.1.6.1.8.18.1.19
		priWanConnCfgPppoePasswordS OBJECT-TYPE
			SYNTAX OCTET STRING
			MAX-ACCESS read-write
			STATUS current
			DESCRIPTION
				"Description."
			::= { priWanConnCfgEntry 19 }

		
--  1.3.6.1.4.1.37950.1.1.6.1.8.18.1.20
		-- 1.3.6.1.4.1.37950.1.1.6.1.8.18.1.20
		priWanConnCfgPppoeSerName OBJECT-TYPE
			SYNTAX OCTET STRING
			MAX-ACCESS read-write
			STATUS current
			DESCRIPTION
				"Description."
			::= { priWanConnCfgEntry 20 }

		
--  1.3.6.1.4.1.37950.1.1.6.1.8.18.1.21
		-- 1.3.6.1.4.1.37950.1.1.6.1.8.18.1.21
		priWanConnCfgPppoeModeS OBJECT-TYPE
			SYNTAX INTEGER
				{
				autoConnect(0),
				connectWhenPayload(1)
				}
			MAX-ACCESS read-write
			STATUS current
			DESCRIPTION
				"Description."
			::= { priWanConnCfgEntry 21 }

		
--  1.3.6.1.4.1.37950.1.1.6.1.8.18.1.22
		-- 1.3.6.1.4.1.37950.1.1.6.1.8.18.1.22
		priWanConnCfgQosEnableS OBJECT-TYPE
			SYNTAX INTEGER
				{
				disable(0),
				enable(1)
				}
			MAX-ACCESS read-write
			STATUS current
			DESCRIPTION
				"Description."
			::= { priWanConnCfgEntry 22 }

		
--  1.3.6.1.4.1.37950.1.1.6.1.8.18.1.23
		-- 1.3.6.1.4.1.37950.1.1.6.1.8.18.1.23
		priWanConnCfgVlanModeS OBJECT-TYPE
			SYNTAX INTEGER
				{
				disable(0),
				tag(1),
				transparent(2)
				}
			MAX-ACCESS read-write
			STATUS current
			DESCRIPTION
				"Description."
			::= { priWanConnCfgEntry 23 }

		
--  1.3.6.1.4.1.37950.1.1.6.1.8.18.1.24
		-- 1.3.6.1.4.1.37950.1.1.6.1.8.18.1.24
		priWanConnCfgTranslationEnableS OBJECT-TYPE
			SYNTAX INTEGER
				{
				disable(0),
				enable(1)
				}
			MAX-ACCESS read-write
			STATUS current
			DESCRIPTION
				"Description."
			::= { priWanConnCfgEntry 24 }

		
--  1.3.6.1.4.1.37950.1.1.6.1.8.18.1.25
		-- 1.3.6.1.4.1.37950.1.1.6.1.8.18.1.25
		priWanConnCfgTranslationVlanS OBJECT-TYPE
			SYNTAX INTEGER (0..4095)
			MAX-ACCESS read-write
			STATUS current
			DESCRIPTION
				"Description."
			::= { priWanConnCfgEntry 25 }

		
--  1.3.6.1.4.1.37950.1.1.6.1.8.18.1.26
		-- 1.3.6.1.4.1.37950.1.1.6.1.8.18.1.26
		priWanConnCfgTranslationCosS OBJECT-TYPE
			SYNTAX INTEGER (0..7)
			MAX-ACCESS read-write
			STATUS current
			DESCRIPTION
				"Description."
			::= { priWanConnCfgEntry 26 }

		
--  1.3.6.1.4.1.37950.1.1.6.1.8.18.1.27
		-- 1.3.6.1.4.1.37950.1.1.6.1.8.18.1.27
		priWanConnCfgQinqEnableS OBJECT-TYPE
			SYNTAX INTEGER
				{
				disable(0),
				enable(1)
				}
			MAX-ACCESS read-write
			STATUS current
			DESCRIPTION
				"Description."
			::= { priWanConnCfgEntry 27 }

		
--  1.3.6.1.4.1.37950.1.1.6.1.8.18.1.28
		-- 1.3.6.1.4.1.37950.1.1.6.1.8.18.1.28
		priWanConnCfgQinqTpidS OBJECT-TYPE
			SYNTAX INTEGER (0..65534)
			MAX-ACCESS read-write
			STATUS current
			DESCRIPTION
				"Description."
			::= { priWanConnCfgEntry 28 }

		
--  1.3.6.1.4.1.37950.1.1.6.1.8.18.1.29
		-- 1.3.6.1.4.1.37950.1.1.6.1.8.18.1.29
		priWanConnCfgSvlanIdS OBJECT-TYPE
			SYNTAX INTEGER (0..4095)
			MAX-ACCESS read-write
			STATUS current
			DESCRIPTION
				"Description."
			::= { priWanConnCfgEntry 29 }

		
--  1.3.6.1.4.1.37950.1.1.6.1.8.18.1.30
		-- 1.3.6.1.4.1.37950.1.1.6.1.8.18.1.30
		priWanConnCfgSvlanCosS OBJECT-TYPE
			SYNTAX INTEGER (0..7)
			MAX-ACCESS read-write
			STATUS current
			DESCRIPTION
				"Description."
			::= { priWanConnCfgEntry 30 }

		
--  1.3.6.1.4.1.37950.1.1.6.1.8.18.1.31
		-- 1.3.6.1.4.1.37950.1.1.6.1.8.18.1.31
		priWanConnCfgName OBJECT-TYPE
			SYNTAX OCTET STRING
			MAX-ACCESS read-write
			STATUS current
			DESCRIPTION
				"Description."
			::= { priWanConnCfgEntry 31 }

		
--  1.3.6.1.4.1.37950.1.1.6.1.8.18.1.32
		-- 1.3.6.1.4.1.37950.1.1.6.1.8.18.1.32
		priWanConnCfgStatus OBJECT-TYPE
			SYNTAX INTEGER
				{
				disconnected(0),
				connected(1)
				}
			MAX-ACCESS read-write
			STATUS current
			DESCRIPTION
				"Description."
			::= { priWanConnCfgEntry 32 }

		
--  1.3.6.1.4.1.37950.1.1.6.1.8.18.1.33
		-- 1.3.6.1.4.1.37950.1.1.6.1.8.18.1.33
		priWanConnCfgMTU OBJECT-TYPE
			SYNTAX Integer32
			MAX-ACCESS read-write
			STATUS current
			DESCRIPTION
				"Description."
			::= { priWanConnCfgEntry 33 }

		
--  1.3.6.1.4.1.37950.1.1.6.1.8.19
		-- 1.3.6.1.4.1.37950.1.1.6.1.8.19
		priWanConnV6Table OBJECT-TYPE
			SYNTAX SEQUENCE OF PriWanConnV6Entry
			MAX-ACCESS not-accessible
			STATUS current
			DESCRIPTION
				"Description."
			::= { gOnuPriCfgInfo 19 }

		
--  1.3.6.1.4.1.37950.1.1.6.1.8.19.1
		-- 1.3.6.1.4.1.37950.1.1.6.1.8.19.1
		priWanConnV6Entry OBJECT-TYPE
			SYNTAX PriWanConnV6Entry
			MAX-ACCESS not-accessible
			STATUS current
			DESCRIPTION
				"Description."
			INDEX { priV6ConnPonS, priV6ConnOnuS, priV6ConnIndexS }
			::= { priWanConnV6Table 1 }

		
		PriWanConnV6Entry ::=
			SEQUENCE { 
				priV6ConnPonS
					INTEGER,
				priV6ConnOnuS
					INTEGER,
				priV6ConnIndexS
					Integer32,
				priV6ConnBindLanS
					INTEGER,
				priV6ConnBindSsidS
					INTEGER,
				priV6WanModeS
					INTEGER,
				priV6ConnTypeS
					INTEGER,
				priV6ConnVlanIdS
					INTEGER,
				priV6ConnVlanCosS
					INTEGER,
				priV6ConnIpProtocolS
					INTEGER,
				priV6wanConnModeS
					INTEGER,
				priV6ConnIpAddressIpv4S
					IpAddress,
				priV6ConnIpNetMaskIpv4S
					IpAddress,
				priV6ConnGatewayIpv4S
					IpAddress,
				priV6ConnDnsEnableIpv4S
					INTEGER,
				priV6ConnMasterDnsIpv4S
					IpAddress,
				priV6ConnSlaveDnsIpv4S
					IpAddress,
				priV6ConnNatEnableS
					INTEGER,
				priV6ConnAddressIpv6S
					OCTET STRING,
				priV6ConnPrefixLenIpv6S
					INTEGER,
				priV6ConnGatewayIpv6S
					OCTET STRING,
				priV6ConnDnsEnableIpv6S
					INTEGER,
				priV6ConnMsaterDnsIpv6S
					OCTET STRING,
				priV6ConnSlaveDnsIpv6S
					OCTET STRING,
				priV6ConnSlaacS
					INTEGER,
				priV6ConnPppoeProxyS
					INTEGER,
				priV6ConnPppoeUsernameS
					OCTET STRING,
				priV6ConnPppoePasswordS
					OCTET STRING,
				priV6ConnPppoeSerNameS
					OCTET STRING,
				priV6ConnPppoeModeS
					INTEGER,
				priV6ConnDhcpv6ClientAddressS
					INTEGER,
				priV6ConnDhcpv6ClientPrefixS
					INTEGER,
				priV6ConnDsLiteEnableS
					INTEGER,
				priV6ConnDsLiteAftrModeS
					INTEGER,
				priV6ConnDsLiteAddressTypeS
					INTEGER,
				priV6ConnDsLiteAddressS
					OCTET STRING,
				priv6ConnQosEnableS
					INTEGER,
				priV6ConnVlanModeS
					INTEGER,
				priV6ConnTranslationEnableS
					INTEGER,
				priV6ConnTranslationVlanS
					INTEGER,
				priV6ConnTranslationCosS
					INTEGER,
				priV6ConnQinqEnableS
					INTEGER,
				priV6ConnQinqTpidS
					INTEGER,
				priV6ConnSvlanIdS
					INTEGER,
				priV6ConnSvlanCosS
					INTEGER,
				priV6ConnRouteMtuS
					Integer32,
				priv6ConnNameS
					OCTET STRING,
				priV6ConnStatusS
					INTEGER,
				priV6ConnMacAddrS
					OCTET STRING
			 }

--  1.3.6.1.4.1.37950.1.1.6.1.8.19.1.1
		-- 1.3.6.1.4.1.37950.1.1.6.1.8.19.1.1
		priV6ConnPonS OBJECT-TYPE
			SYNTAX INTEGER (1..16)
			MAX-ACCESS read-write
			STATUS current
			DESCRIPTION
				"Description."
			::= { priWanConnV6Entry 1 }

		
--  1.3.6.1.4.1.37950.1.1.6.1.8.19.1.2
		-- 1.3.6.1.4.1.37950.1.1.6.1.8.19.1.2
		priV6ConnOnuS OBJECT-TYPE
			SYNTAX INTEGER (1..65535)
			MAX-ACCESS read-write
			STATUS current
			DESCRIPTION
				"Description."
			::= { priWanConnV6Entry 2 }

		
--  1.3.6.1.4.1.37950.1.1.6.1.8.19.1.3
		-- 1.3.6.1.4.1.37950.1.1.6.1.8.19.1.3
		priV6ConnIndexS OBJECT-TYPE
			SYNTAX Integer32 (1..8)
			MAX-ACCESS read-write
			STATUS current
			DESCRIPTION
				"Description."
			::= { priWanConnV6Entry 3 }

		
--  1.3.6.1.4.1.37950.1.1.6.1.8.19.1.4
		-- 1.3.6.1.4.1.37950.1.1.6.1.8.19.1.4
		priV6ConnBindLanS OBJECT-TYPE
			SYNTAX INTEGER (0..65535)
			MAX-ACCESS read-write
			STATUS current
			DESCRIPTION
				"Description."
			::= { priWanConnV6Entry 4 }

		
--  1.3.6.1.4.1.37950.1.1.6.1.8.19.1.5
		-- 1.3.6.1.4.1.37950.1.1.6.1.8.19.1.5
		priV6ConnBindSsidS OBJECT-TYPE
			SYNTAX INTEGER (0..65535)
			MAX-ACCESS read-write
			STATUS current
			DESCRIPTION
				"Description."
			::= { priWanConnV6Entry 5 }

		
--  1.3.6.1.4.1.37950.1.1.6.1.8.19.1.6
		-- 1.3.6.1.4.1.37950.1.1.6.1.8.19.1.6
		priV6WanModeS OBJECT-TYPE
			SYNTAX INTEGER
				{
				internet(0),
				multicast(1),
				tr069(2),
				tr069_internet(3),
				tr069_voip(4),
				voip_internet(5),
				tr069_voip_internet(6),
				voip(7),
				other(100)
				}
			MAX-ACCESS read-write
			STATUS current
			DESCRIPTION
				"Description."
			::= { priWanConnV6Entry 6 }

		
--  1.3.6.1.4.1.37950.1.1.6.1.8.19.1.7
		-- 1.3.6.1.4.1.37950.1.1.6.1.8.19.1.7
		priV6ConnTypeS OBJECT-TYPE
			SYNTAX INTEGER
				{
				bridge(0),
				route(1)
				}
			MAX-ACCESS read-write
			STATUS current
			DESCRIPTION
				"Description."
			::= { priWanConnV6Entry 7 }

		
--  1.3.6.1.4.1.37950.1.1.6.1.8.19.1.8
		-- 1.3.6.1.4.1.37950.1.1.6.1.8.19.1.8
		priV6ConnVlanIdS OBJECT-TYPE
			SYNTAX INTEGER (0..4095)
			MAX-ACCESS read-write
			STATUS current
			DESCRIPTION
				"Description."
			::= { priWanConnV6Entry 8 }

		
--  1.3.6.1.4.1.37950.1.1.6.1.8.19.1.9
		-- 1.3.6.1.4.1.37950.1.1.6.1.8.19.1.9
		priV6ConnVlanCosS OBJECT-TYPE
			SYNTAX INTEGER (0..7)
			MAX-ACCESS read-write
			STATUS current
			DESCRIPTION
				"Description."
			::= { priWanConnV6Entry 9 }

		
--  1.3.6.1.4.1.37950.1.1.6.1.8.19.1.10
		-- 1.3.6.1.4.1.37950.1.1.6.1.8.19.1.10
		priV6ConnIpProtocolS OBJECT-TYPE
			SYNTAX INTEGER
				{
				ipv4(0),
				ipv6(1),
				ipv4_ipv6(2)
				}
			MAX-ACCESS read-write
			STATUS current
			DESCRIPTION
				"Description."
			::= { priWanConnV6Entry 10 }

		
--  1.3.6.1.4.1.37950.1.1.6.1.8.19.1.11
		-- 1.3.6.1.4.1.37950.1.1.6.1.8.19.1.11
		priV6wanConnModeS OBJECT-TYPE
			SYNTAX INTEGER
				{
				dhcp(0),
				static(1),
				pppoe(2)
				}
			MAX-ACCESS read-write
			STATUS current
			DESCRIPTION
				"Description."
			::= { priWanConnV6Entry 11 }

		
--  1.3.6.1.4.1.37950.1.1.6.1.8.19.1.12
		-- 1.3.6.1.4.1.37950.1.1.6.1.8.19.1.12
		priV6ConnIpAddressIpv4S OBJECT-TYPE
			SYNTAX IpAddress
			MAX-ACCESS read-write
			STATUS current
			DESCRIPTION
				"Description."
			::= { priWanConnV6Entry 12 }

		
--  1.3.6.1.4.1.37950.1.1.6.1.8.19.1.13
		-- 1.3.6.1.4.1.37950.1.1.6.1.8.19.1.13
		priV6ConnIpNetMaskIpv4S OBJECT-TYPE
			SYNTAX IpAddress
			MAX-ACCESS read-write
			STATUS current
			DESCRIPTION
				"Description."
			::= { priWanConnV6Entry 13 }

		
--  1.3.6.1.4.1.37950.1.1.6.1.8.19.1.14
		-- 1.3.6.1.4.1.37950.1.1.6.1.8.19.1.14
		priV6ConnGatewayIpv4S OBJECT-TYPE
			SYNTAX IpAddress
			MAX-ACCESS read-write
			STATUS current
			DESCRIPTION
				"Description."
			::= { priWanConnV6Entry 14 }

		
--  1.3.6.1.4.1.37950.1.1.6.1.8.19.1.15
		-- 1.3.6.1.4.1.37950.1.1.6.1.8.19.1.15
		priV6ConnDnsEnableIpv4S OBJECT-TYPE
			SYNTAX INTEGER
				{
				disable(0),
				enable(1)
				}
			MAX-ACCESS read-write
			STATUS current
			DESCRIPTION
				"Description."
			::= { priWanConnV6Entry 15 }

		
--  1.3.6.1.4.1.37950.1.1.6.1.8.19.1.16
		-- 1.3.6.1.4.1.37950.1.1.6.1.8.19.1.16
		priV6ConnMasterDnsIpv4S OBJECT-TYPE
			SYNTAX IpAddress
			MAX-ACCESS read-write
			STATUS current
			DESCRIPTION
				"Description."
			::= { priWanConnV6Entry 16 }

		
--  1.3.6.1.4.1.37950.1.1.6.1.8.19.1.17
		-- 1.3.6.1.4.1.37950.1.1.6.1.8.19.1.17
		priV6ConnSlaveDnsIpv4S OBJECT-TYPE
			SYNTAX IpAddress
			MAX-ACCESS read-write
			STATUS current
			DESCRIPTION
				"Description."
			::= { priWanConnV6Entry 17 }

		
--  1.3.6.1.4.1.37950.1.1.6.1.8.19.1.18
		-- 1.3.6.1.4.1.37950.1.1.6.1.8.19.1.18
		priV6ConnNatEnableS OBJECT-TYPE
			SYNTAX INTEGER
				{
				disable(0),
				enable(1)
				}
			MAX-ACCESS read-write
			STATUS current
			DESCRIPTION
				"Description."
			::= { priWanConnV6Entry 18 }

		
--  1.3.6.1.4.1.37950.1.1.6.1.8.19.1.19
		-- 1.3.6.1.4.1.37950.1.1.6.1.8.19.1.19
		priV6ConnAddressIpv6S OBJECT-TYPE
			SYNTAX OCTET STRING
			MAX-ACCESS read-write
			STATUS current
			DESCRIPTION
				"Description."
			::= { priWanConnV6Entry 19 }

		
--  1.3.6.1.4.1.37950.1.1.6.1.8.19.1.20
		-- 1.3.6.1.4.1.37950.1.1.6.1.8.19.1.20
		priV6ConnPrefixLenIpv6S OBJECT-TYPE
			SYNTAX INTEGER (0..128)
			MAX-ACCESS read-write
			STATUS current
			DESCRIPTION
				"Description."
			::= { priWanConnV6Entry 20 }

		
--  1.3.6.1.4.1.37950.1.1.6.1.8.19.1.21
		-- 1.3.6.1.4.1.37950.1.1.6.1.8.19.1.21
		priV6ConnGatewayIpv6S OBJECT-TYPE
			SYNTAX OCTET STRING
			MAX-ACCESS read-write
			STATUS current
			DESCRIPTION
				"Description."
			::= { priWanConnV6Entry 21 }

		
--  1.3.6.1.4.1.37950.1.1.6.1.8.19.1.22
		-- 1.3.6.1.4.1.37950.1.1.6.1.8.19.1.22
		priV6ConnDnsEnableIpv6S OBJECT-TYPE
			SYNTAX INTEGER
				{
				disable(0),
				enable(1)
				}
			MAX-ACCESS read-write
			STATUS current
			DESCRIPTION
				"Description."
			::= { priWanConnV6Entry 22 }

		
--  1.3.6.1.4.1.37950.1.1.6.1.8.19.1.23
		-- 1.3.6.1.4.1.37950.1.1.6.1.8.19.1.23
		priV6ConnMsaterDnsIpv6S OBJECT-TYPE
			SYNTAX OCTET STRING
			MAX-ACCESS read-write
			STATUS current
			DESCRIPTION
				"Description."
			::= { priWanConnV6Entry 23 }

		
--  1.3.6.1.4.1.37950.1.1.6.1.8.19.1.24
		-- 1.3.6.1.4.1.37950.1.1.6.1.8.19.1.24
		priV6ConnSlaveDnsIpv6S OBJECT-TYPE
			SYNTAX OCTET STRING
			MAX-ACCESS read-write
			STATUS current
			DESCRIPTION
				"Description."
			::= { priWanConnV6Entry 24 }

		
--  1.3.6.1.4.1.37950.1.1.6.1.8.19.1.25
		-- 1.3.6.1.4.1.37950.1.1.6.1.8.19.1.25
		priV6ConnSlaacS OBJECT-TYPE
			SYNTAX INTEGER
				{
				disable(0),
				enable(1)
				}
			MAX-ACCESS read-write
			STATUS current
			DESCRIPTION
				"Description."
			::= { priWanConnV6Entry 25 }

		
--  1.3.6.1.4.1.37950.1.1.6.1.8.19.1.26
		-- 1.3.6.1.4.1.37950.1.1.6.1.8.19.1.26
		priV6ConnPppoeProxyS OBJECT-TYPE
			SYNTAX INTEGER
				{
				disable(0),
				enable(1)
				}
			MAX-ACCESS read-write
			STATUS current
			DESCRIPTION
				"Description."
			::= { priWanConnV6Entry 26 }

		
--  1.3.6.1.4.1.37950.1.1.6.1.8.19.1.27
		-- 1.3.6.1.4.1.37950.1.1.6.1.8.19.1.27
		priV6ConnPppoeUsernameS OBJECT-TYPE
			SYNTAX OCTET STRING
			MAX-ACCESS read-write
			STATUS current
			DESCRIPTION
				"Description."
			::= { priWanConnV6Entry 27 }

		
--  1.3.6.1.4.1.37950.1.1.6.1.8.19.1.28
		-- 1.3.6.1.4.1.37950.1.1.6.1.8.19.1.28
		priV6ConnPppoePasswordS OBJECT-TYPE
			SYNTAX OCTET STRING
			MAX-ACCESS read-write
			STATUS current
			DESCRIPTION
				"Description."
			::= { priWanConnV6Entry 28 }

		
--  1.3.6.1.4.1.37950.1.1.6.1.8.19.1.29
		-- 1.3.6.1.4.1.37950.1.1.6.1.8.19.1.29
		priV6ConnPppoeSerNameS OBJECT-TYPE
			SYNTAX OCTET STRING
			MAX-ACCESS read-write
			STATUS current
			DESCRIPTION
				"Description."
			::= { priWanConnV6Entry 29 }

		
--  1.3.6.1.4.1.37950.1.1.6.1.8.19.1.30
		-- 1.3.6.1.4.1.37950.1.1.6.1.8.19.1.30
		priV6ConnPppoeModeS OBJECT-TYPE
			SYNTAX INTEGER
				{
				autoConnect(0),
				flowConnect(1)
				}
			MAX-ACCESS read-write
			STATUS current
			DESCRIPTION
				"Description."
			::= { priWanConnV6Entry 30 }

		
--  1.3.6.1.4.1.37950.1.1.6.1.8.19.1.31
		-- 1.3.6.1.4.1.37950.1.1.6.1.8.19.1.31
		priV6ConnDhcpv6ClientAddressS OBJECT-TYPE
			SYNTAX INTEGER
				{
				disable(0),
				enable(1)
				}
			MAX-ACCESS read-write
			STATUS current
			DESCRIPTION
				"Description."
			::= { priWanConnV6Entry 31 }

		
--  1.3.6.1.4.1.37950.1.1.6.1.8.19.1.32
		-- 1.3.6.1.4.1.37950.1.1.6.1.8.19.1.32
		priV6ConnDhcpv6ClientPrefixS OBJECT-TYPE
			SYNTAX INTEGER
				{
				disable(0),
				enable(1)
				}
			MAX-ACCESS read-write
			STATUS current
			DESCRIPTION
				"Description."
			::= { priWanConnV6Entry 32 }

		
--  1.3.6.1.4.1.37950.1.1.6.1.8.19.1.33
		-- 1.3.6.1.4.1.37950.1.1.6.1.8.19.1.33
		priV6ConnDsLiteEnableS OBJECT-TYPE
			SYNTAX INTEGER
				{
				disable(0),
				enable(1)
				}
			MAX-ACCESS read-write
			STATUS current
			DESCRIPTION
				"Description."
			::= { priWanConnV6Entry 33 }

		
--  1.3.6.1.4.1.37950.1.1.6.1.8.19.1.34
		-- 1.3.6.1.4.1.37950.1.1.6.1.8.19.1.34
		priV6ConnDsLiteAftrModeS OBJECT-TYPE
			SYNTAX INTEGER
				{
				dhcpv6(0),
				manual(1)
				}
			MAX-ACCESS read-write
			STATUS current
			DESCRIPTION
				"Description."
			::= { priWanConnV6Entry 34 }

		
--  1.3.6.1.4.1.37950.1.1.6.1.8.19.1.35
		-- 1.3.6.1.4.1.37950.1.1.6.1.8.19.1.35
		priV6ConnDsLiteAddressTypeS OBJECT-TYPE
			SYNTAX INTEGER
				{
				ipv6(0),
				dns(1)
				}
			MAX-ACCESS read-write
			STATUS current
			DESCRIPTION
				"Description."
			::= { priWanConnV6Entry 35 }

		
--  1.3.6.1.4.1.37950.1.1.6.1.8.19.1.36
		-- 1.3.6.1.4.1.37950.1.1.6.1.8.19.1.36
		priV6ConnDsLiteAddressS OBJECT-TYPE
			SYNTAX OCTET STRING
			MAX-ACCESS read-write
			STATUS current
			DESCRIPTION
				"Description."
			::= { priWanConnV6Entry 36 }

		
--  1.3.6.1.4.1.37950.1.1.6.1.8.19.1.37
		-- 1.3.6.1.4.1.37950.1.1.6.1.8.19.1.37
		priv6ConnQosEnableS OBJECT-TYPE
			SYNTAX INTEGER
				{
				disable(0),
				enable(1)
				}
			MAX-ACCESS read-write
			STATUS current
			DESCRIPTION
				"Description."
			::= { priWanConnV6Entry 37 }

		
--  1.3.6.1.4.1.37950.1.1.6.1.8.19.1.38
		-- 1.3.6.1.4.1.37950.1.1.6.1.8.19.1.38
		priV6ConnVlanModeS OBJECT-TYPE
			SYNTAX INTEGER
				{
				disable(0),
				tag(1),
				transparent(2)
				}
			MAX-ACCESS read-write
			STATUS current
			DESCRIPTION
				"Description."
			::= { priWanConnV6Entry 38 }

		
--  1.3.6.1.4.1.37950.1.1.6.1.8.19.1.39
		-- 1.3.6.1.4.1.37950.1.1.6.1.8.19.1.39
		priV6ConnTranslationEnableS OBJECT-TYPE
			SYNTAX INTEGER
				{
				disable(0),
				enable(1)
				}
			MAX-ACCESS read-write
			STATUS current
			DESCRIPTION
				"Description."
			::= { priWanConnV6Entry 39 }

		
--  1.3.6.1.4.1.37950.1.1.6.1.8.19.1.40
		-- 1.3.6.1.4.1.37950.1.1.6.1.8.19.1.40
		priV6ConnTranslationVlanS OBJECT-TYPE
			SYNTAX INTEGER (1..4095)
			MAX-ACCESS read-write
			STATUS current
			DESCRIPTION
				"Description."
			::= { priWanConnV6Entry 40 }

		
--  1.3.6.1.4.1.37950.1.1.6.1.8.19.1.41
		-- 1.3.6.1.4.1.37950.1.1.6.1.8.19.1.41
		priV6ConnTranslationCosS OBJECT-TYPE
			SYNTAX INTEGER (0..7)
			MAX-ACCESS read-write
			STATUS current
			DESCRIPTION
				"Description."
			::= { priWanConnV6Entry 41 }

		
--  1.3.6.1.4.1.37950.1.1.6.1.8.19.1.42
		-- 1.3.6.1.4.1.37950.1.1.6.1.8.19.1.42
		priV6ConnQinqEnableS OBJECT-TYPE
			SYNTAX INTEGER
				{
				disable(0),
				enable(1)
				}
			MAX-ACCESS read-write
			STATUS current
			DESCRIPTION
				"Description."
			::= { priWanConnV6Entry 42 }

		
--  1.3.6.1.4.1.37950.1.1.6.1.8.19.1.43
		-- 1.3.6.1.4.1.37950.1.1.6.1.8.19.1.43
		priV6ConnQinqTpidS OBJECT-TYPE
			SYNTAX INTEGER (1..65534)
			MAX-ACCESS read-write
			STATUS current
			DESCRIPTION
				"Description."
			::= { priWanConnV6Entry 43 }

		
--  1.3.6.1.4.1.37950.1.1.6.1.8.19.1.44
		-- 1.3.6.1.4.1.37950.1.1.6.1.8.19.1.44
		priV6ConnSvlanIdS OBJECT-TYPE
			SYNTAX INTEGER (1..4095)
			MAX-ACCESS read-write
			STATUS current
			DESCRIPTION
				"Description."
			::= { priWanConnV6Entry 44 }

		
--  1.3.6.1.4.1.37950.1.1.6.1.8.19.1.45
		-- 1.3.6.1.4.1.37950.1.1.6.1.8.19.1.45
		priV6ConnSvlanCosS OBJECT-TYPE
			SYNTAX INTEGER (0..7)
			MAX-ACCESS read-write
			STATUS current
			DESCRIPTION
				"Description."
			::= { priWanConnV6Entry 45 }

		
--  1.3.6.1.4.1.37950.1.1.6.1.8.19.1.46
		-- 1.3.6.1.4.1.37950.1.1.6.1.8.19.1.46
		priV6ConnRouteMtuS OBJECT-TYPE
			SYNTAX Integer32 (0 | 576..1500)
			MAX-ACCESS read-write
			STATUS current
			DESCRIPTION
				"Description."
			::= { priWanConnV6Entry 46 }

		
--  1.3.6.1.4.1.37950.1.1.6.1.8.19.1.47
		-- 1.3.6.1.4.1.37950.1.1.6.1.8.19.1.47
		priv6ConnNameS OBJECT-TYPE
			SYNTAX OCTET STRING
			MAX-ACCESS read-write
			STATUS current
			DESCRIPTION
				"Description."
			::= { priWanConnV6Entry 47 }

		
--  1.3.6.1.4.1.37950.1.1.6.1.8.19.1.48
		-- 1.3.6.1.4.1.37950.1.1.6.1.8.19.1.48
		priV6ConnStatusS OBJECT-TYPE
			SYNTAX INTEGER
				{
				disconnected(0),
				connected(1)
				}
			MAX-ACCESS read-write
			STATUS current
			DESCRIPTION
				"Description."
			::= { priWanConnV6Entry 48 }

		
--  1.3.6.1.4.1.37950.1.1.6.1.8.19.1.49
		-- 1.3.6.1.4.1.37950.1.1.6.1.8.19.1.49
		priV6ConnMacAddrS OBJECT-TYPE
			SYNTAX OCTET STRING
			MAX-ACCESS read-write
			STATUS current
			DESCRIPTION
				"Description."
			::= { priWanConnV6Entry 49 }

		
--  1.3.6.1.4.1.37950.1.1.6.1.8.20
		-- 1.3.6.1.4.1.37950.1.1.6.1.8.20
		priWanConnV6CfgTable OBJECT-TYPE
			SYNTAX SEQUENCE OF PriWanConnV6CfgEntry
			MAX-ACCESS not-accessible
			STATUS current
			DESCRIPTION
				"Description."
			::= { gOnuPriCfgInfo 20 }

		
--  1.3.6.1.4.1.37950.1.1.6.1.8.20.1
		-- 1.3.6.1.4.1.37950.1.1.6.1.8.20.1
		priWanConnV6CfgEntry OBJECT-TYPE
			SYNTAX PriWanConnV6CfgEntry
			MAX-ACCESS not-accessible
			STATUS current
			DESCRIPTION
				"Description."
			INDEX { priV6ConnCfgPonS, priV6ConnCfgOnuS, priV6ConnCfgIndexS }
			::= { priWanConnV6CfgTable 1 }

		
		PriWanConnV6CfgEntry ::=
			SEQUENCE { 
				priV6ConnCfgPonS
					INTEGER,
				priV6ConnCfgOnuS
					INTEGER,
				priV6ConnCfgIndexS
					Integer32,
				priV6ConnCfgBindLanS
					INTEGER,
				priV6ConnCfgBindSsidS
					INTEGER,
				priV6CfgWanModeS
					INTEGER,
				priV6ConnCfgTypeS
					INTEGER,
				priV6ConnCfgVlanIdS
					INTEGER,
				priV6ConnCfgVlanCosS
					INTEGER,
				priV6ConnCfgIpProtocolS
					INTEGER,
				priV6wanConnCfgModeS
					INTEGER,
				priV6ConnCfgIpAddressIpv4S
					IpAddress,
				priV6ConnCfgIpNetMaskIpv4S
					IpAddress,
				priV6ConnCfgGatewayIpv4S
					IpAddress,
				priV6ConnCfgDnsEnableIpv4S
					INTEGER,
				priV6ConnCfgMasterDnsIpv4S
					IpAddress,
				priV6ConnCfgSlaveDnsIpv4S
					IpAddress,
				priV6ConnCfgNatEnableS
					INTEGER,
				priV6ConnCfgAddressIpv6S
					OCTET STRING,
				priV6ConnCfgPrefixLenIpv6S
					INTEGER,
				priV6ConnCfgGatewayIpv6S
					OCTET STRING,
				priV6ConnCfgDnsEnableIpv6S
					INTEGER,
				priV6ConnCfgMsaterDnsIpv6S
					OCTET STRING,
				priV6ConnCfgSlaveDnsIpv6S
					OCTET STRING,
				priV6ConnCfgSlaacS
					INTEGER,
				priV6ConnCfgPppoeProxyS
					INTEGER,
				priV6ConnCfgPppoeUsernameS
					OCTET STRING,
				priV6ConnCfgPppoePasswordS
					OCTET STRING,
				priV6ConnCfgPppoeSerNameS
					OCTET STRING,
				priV6ConnCfgPppoeModeS
					INTEGER,
				priV6ConnCfgDhcpv6ClientAddressS
					INTEGER,
				priV6ConnCfgDhcpv6ClientPrefixS
					INTEGER,
				priV6ConnCfgDsLiteEnableS
					INTEGER,
				priV6ConnCfgDsLiteAftrModeS
					INTEGER,
				priV6ConnCfgDsLiteAddressTypeS
					INTEGER,
				priV6ConnCfgDsLiteAddressS
					OCTET STRING,
				priv6ConnCfgQosEnableS
					INTEGER,
				priV6ConnCfgVlanModeS
					INTEGER,
				priV6ConnCfgTranslationEnableS
					INTEGER,
				priV6ConnCfgTranslationVlanS
					INTEGER,
				priV6ConnCfgTranslationCosS
					INTEGER,
				priV6ConnCfgQinqEnableS
					INTEGER,
				priV6ConnCfgQinqTpidS
					INTEGER,
				priV6ConnCfgSvlanIdS
					INTEGER,
				priV6ConnCfgSvlanCosS
					INTEGER,
				priV6ConnCfgRouteMtuS
					Integer32
			 }

--  1.3.6.1.4.1.37950.1.1.6.1.8.20.1.1
		-- 1.3.6.1.4.1.37950.1.1.6.1.8.20.1.1
		priV6ConnCfgPonS OBJECT-TYPE
			SYNTAX INTEGER (1..16)
			MAX-ACCESS read-write
			STATUS current
			DESCRIPTION
				"Description."
			::= { priWanConnV6CfgEntry 1 }

		
--  1.3.6.1.4.1.37950.1.1.6.1.8.20.1.2
		-- 1.3.6.1.4.1.37950.1.1.6.1.8.20.1.2
		priV6ConnCfgOnuS OBJECT-TYPE
			SYNTAX INTEGER (1..65535)
			MAX-ACCESS read-write
			STATUS current
			DESCRIPTION
				"Description."
			::= { priWanConnV6CfgEntry 2 }

		
--  1.3.6.1.4.1.37950.1.1.6.1.8.20.1.3
		-- 1.3.6.1.4.1.37950.1.1.6.1.8.20.1.3
		priV6ConnCfgIndexS OBJECT-TYPE
			SYNTAX Integer32 (1..8)
			MAX-ACCESS read-write
			STATUS current
			DESCRIPTION
				"Description."
			::= { priWanConnV6CfgEntry 3 }

		
--  1.3.6.1.4.1.37950.1.1.6.1.8.20.1.4
		-- 1.3.6.1.4.1.37950.1.1.6.1.8.20.1.4
		priV6ConnCfgBindLanS OBJECT-TYPE
			SYNTAX INTEGER (0..65535)
			MAX-ACCESS read-write
			STATUS current
			DESCRIPTION
				"Description."
			::= { priWanConnV6CfgEntry 4 }

		
--  1.3.6.1.4.1.37950.1.1.6.1.8.20.1.5
		-- 1.3.6.1.4.1.37950.1.1.6.1.8.20.1.5
		priV6ConnCfgBindSsidS OBJECT-TYPE
			SYNTAX INTEGER (0..65535)
			MAX-ACCESS read-write
			STATUS current
			DESCRIPTION
				"Description."
			::= { priWanConnV6CfgEntry 5 }

		
--  1.3.6.1.4.1.37950.1.1.6.1.8.20.1.6
		-- 1.3.6.1.4.1.37950.1.1.6.1.8.20.1.6
		priV6CfgWanModeS OBJECT-TYPE
			SYNTAX INTEGER
				{
				internet(0),
				multicast(1),
				tr069(2),
				tr069_internet(3),
				tr069_voip(4),
				voip_internet(5),
				tr069_voip_internet(6),
				voip(7),
				other(100)
				}
			MAX-ACCESS read-write
			STATUS current
			DESCRIPTION
				"Description."
			::= { priWanConnV6CfgEntry 6 }

		
--  1.3.6.1.4.1.37950.1.1.6.1.8.20.1.7
		-- 1.3.6.1.4.1.37950.1.1.6.1.8.20.1.7
		priV6ConnCfgTypeS OBJECT-TYPE
			SYNTAX INTEGER
				{
				bridge(0),
				route(1)
				}
			MAX-ACCESS read-write
			STATUS current
			DESCRIPTION
				"Description."
			::= { priWanConnV6CfgEntry 7 }

		
--  1.3.6.1.4.1.37950.1.1.6.1.8.20.1.8
		-- 1.3.6.1.4.1.37950.1.1.6.1.8.20.1.8
		priV6ConnCfgVlanIdS OBJECT-TYPE
			SYNTAX INTEGER (0..4095)
			MAX-ACCESS read-write
			STATUS current
			DESCRIPTION
				"Description."
			::= { priWanConnV6CfgEntry 8 }

		
--  1.3.6.1.4.1.37950.1.1.6.1.8.20.1.9
		-- 1.3.6.1.4.1.37950.1.1.6.1.8.20.1.9
		priV6ConnCfgVlanCosS OBJECT-TYPE
			SYNTAX INTEGER (0..7)
			MAX-ACCESS read-write
			STATUS current
			DESCRIPTION
				"Description."
			::= { priWanConnV6CfgEntry 9 }

		
--  1.3.6.1.4.1.37950.1.1.6.1.8.20.1.10
		-- 1.3.6.1.4.1.37950.1.1.6.1.8.20.1.10
		priV6ConnCfgIpProtocolS OBJECT-TYPE
			SYNTAX INTEGER
				{
				ipv4(0),
				ipv6(1),
				ipv4_ipv6(2)
				}
			MAX-ACCESS read-write
			STATUS current
			DESCRIPTION
				"Description."
			::= { priWanConnV6CfgEntry 10 }

		
--  1.3.6.1.4.1.37950.1.1.6.1.8.20.1.11
		-- 1.3.6.1.4.1.37950.1.1.6.1.8.20.1.11
		priV6wanConnCfgModeS OBJECT-TYPE
			SYNTAX INTEGER
				{
				dhcp(0),
				static(1),
				pppoe(2)
				}
			MAX-ACCESS read-write
			STATUS current
			DESCRIPTION
				"Description."
			::= { priWanConnV6CfgEntry 11 }

		
--  1.3.6.1.4.1.37950.1.1.6.1.8.20.1.12
		-- 1.3.6.1.4.1.37950.1.1.6.1.8.20.1.12
		priV6ConnCfgIpAddressIpv4S OBJECT-TYPE
			SYNTAX IpAddress
			MAX-ACCESS read-write
			STATUS current
			DESCRIPTION
				"Description."
			::= { priWanConnV6CfgEntry 12 }

		
--  1.3.6.1.4.1.37950.1.1.6.1.8.20.1.13
		-- 1.3.6.1.4.1.37950.1.1.6.1.8.20.1.13
		priV6ConnCfgIpNetMaskIpv4S OBJECT-TYPE
			SYNTAX IpAddress
			MAX-ACCESS read-write
			STATUS current
			DESCRIPTION
				"Description."
			::= { priWanConnV6CfgEntry 13 }

		
--  1.3.6.1.4.1.37950.1.1.6.1.8.20.1.14
		-- 1.3.6.1.4.1.37950.1.1.6.1.8.20.1.14
		priV6ConnCfgGatewayIpv4S OBJECT-TYPE
			SYNTAX IpAddress
			MAX-ACCESS read-write
			STATUS current
			DESCRIPTION
				"Description."
			::= { priWanConnV6CfgEntry 14 }

		
--  1.3.6.1.4.1.37950.1.1.6.1.8.20.1.15
		-- 1.3.6.1.4.1.37950.1.1.6.1.8.20.1.15
		priV6ConnCfgDnsEnableIpv4S OBJECT-TYPE
			SYNTAX INTEGER
				{
				disable(0),
				enable(1)
				}
			MAX-ACCESS read-write
			STATUS current
			DESCRIPTION
				"Description."
			::= { priWanConnV6CfgEntry 15 }

		
--  1.3.6.1.4.1.37950.1.1.6.1.8.20.1.16
		-- 1.3.6.1.4.1.37950.1.1.6.1.8.20.1.16
		priV6ConnCfgMasterDnsIpv4S OBJECT-TYPE
			SYNTAX IpAddress
			MAX-ACCESS read-write
			STATUS current
			DESCRIPTION
				"Description."
			::= { priWanConnV6CfgEntry 16 }

		
--  1.3.6.1.4.1.37950.1.1.6.1.8.20.1.17
		-- 1.3.6.1.4.1.37950.1.1.6.1.8.20.1.17
		priV6ConnCfgSlaveDnsIpv4S OBJECT-TYPE
			SYNTAX IpAddress
			MAX-ACCESS read-write
			STATUS current
			DESCRIPTION
				"Description."
			::= { priWanConnV6CfgEntry 17 }

		
--  1.3.6.1.4.1.37950.1.1.6.1.8.20.1.18
		-- 1.3.6.1.4.1.37950.1.1.6.1.8.20.1.18
		priV6ConnCfgNatEnableS OBJECT-TYPE
			SYNTAX INTEGER
				{
				disable(0),
				enable(1)
				}
			MAX-ACCESS read-write
			STATUS current
			DESCRIPTION
				"Description."
			::= { priWanConnV6CfgEntry 18 }

		
--  1.3.6.1.4.1.37950.1.1.6.1.8.20.1.19
		-- 1.3.6.1.4.1.37950.1.1.6.1.8.20.1.19
		priV6ConnCfgAddressIpv6S OBJECT-TYPE
			SYNTAX OCTET STRING
			MAX-ACCESS read-write
			STATUS current
			DESCRIPTION
				"Description."
			::= { priWanConnV6CfgEntry 19 }

		
--  1.3.6.1.4.1.37950.1.1.6.1.8.20.1.20
		-- 1.3.6.1.4.1.37950.1.1.6.1.8.20.1.20
		priV6ConnCfgPrefixLenIpv6S OBJECT-TYPE
			SYNTAX INTEGER (0..128)
			MAX-ACCESS read-write
			STATUS current
			DESCRIPTION
				"Description."
			::= { priWanConnV6CfgEntry 20 }

		
--  1.3.6.1.4.1.37950.1.1.6.1.8.20.1.21
		-- 1.3.6.1.4.1.37950.1.1.6.1.8.20.1.21
		priV6ConnCfgGatewayIpv6S OBJECT-TYPE
			SYNTAX OCTET STRING
			MAX-ACCESS read-write
			STATUS current
			DESCRIPTION
				"Description."
			::= { priWanConnV6CfgEntry 21 }

		
--  1.3.6.1.4.1.37950.1.1.6.1.8.20.1.22
		-- 1.3.6.1.4.1.37950.1.1.6.1.8.20.1.22
		priV6ConnCfgDnsEnableIpv6S OBJECT-TYPE
			SYNTAX INTEGER
				{
				disable(0),
				enable(1)
				}
			MAX-ACCESS read-write
			STATUS current
			DESCRIPTION
				"Description."
			::= { priWanConnV6CfgEntry 22 }

		
--  1.3.6.1.4.1.37950.1.1.6.1.8.20.1.23
		-- 1.3.6.1.4.1.37950.1.1.6.1.8.20.1.23
		priV6ConnCfgMsaterDnsIpv6S OBJECT-TYPE
			SYNTAX OCTET STRING
			MAX-ACCESS read-write
			STATUS current
			DESCRIPTION
				"Description."
			::= { priWanConnV6CfgEntry 23 }

		
--  1.3.6.1.4.1.37950.1.1.6.1.8.20.1.24
		-- 1.3.6.1.4.1.37950.1.1.6.1.8.20.1.24
		priV6ConnCfgSlaveDnsIpv6S OBJECT-TYPE
			SYNTAX OCTET STRING
			MAX-ACCESS read-write
			STATUS current
			DESCRIPTION
				"Description."
			::= { priWanConnV6CfgEntry 24 }

		
--  1.3.6.1.4.1.37950.1.1.6.1.8.20.1.25
		-- 1.3.6.1.4.1.37950.1.1.6.1.8.20.1.25
		priV6ConnCfgSlaacS OBJECT-TYPE
			SYNTAX INTEGER
				{
				disable(0),
				enable(1)
				}
			MAX-ACCESS read-write
			STATUS current
			DESCRIPTION
				"Description."
			::= { priWanConnV6CfgEntry 25 }

		
--  1.3.6.1.4.1.37950.1.1.6.1.8.20.1.26
		-- 1.3.6.1.4.1.37950.1.1.6.1.8.20.1.26
		priV6ConnCfgPppoeProxyS OBJECT-TYPE
			SYNTAX INTEGER
				{
				disable(0),
				enable(1)
				}
			MAX-ACCESS read-write
			STATUS current
			DESCRIPTION
				"Description."
			::= { priWanConnV6CfgEntry 26 }

		
--  1.3.6.1.4.1.37950.1.1.6.1.8.20.1.27
		-- 1.3.6.1.4.1.37950.1.1.6.1.8.20.1.27
		priV6ConnCfgPppoeUsernameS OBJECT-TYPE
			SYNTAX OCTET STRING
			MAX-ACCESS read-write
			STATUS current
			DESCRIPTION
				"Description."
			::= { priWanConnV6CfgEntry 27 }

		
--  1.3.6.1.4.1.37950.1.1.6.1.8.20.1.28
		-- 1.3.6.1.4.1.37950.1.1.6.1.8.20.1.28
		priV6ConnCfgPppoePasswordS OBJECT-TYPE
			SYNTAX OCTET STRING
			MAX-ACCESS read-write
			STATUS current
			DESCRIPTION
				"Description."
			::= { priWanConnV6CfgEntry 28 }

		
--  1.3.6.1.4.1.37950.1.1.6.1.8.20.1.29
		-- 1.3.6.1.4.1.37950.1.1.6.1.8.20.1.29
		priV6ConnCfgPppoeSerNameS OBJECT-TYPE
			SYNTAX OCTET STRING
			MAX-ACCESS read-write
			STATUS current
			DESCRIPTION
				"Description."
			::= { priWanConnV6CfgEntry 29 }

		
--  1.3.6.1.4.1.37950.1.1.6.1.8.20.1.30
		-- 1.3.6.1.4.1.37950.1.1.6.1.8.20.1.30
		priV6ConnCfgPppoeModeS OBJECT-TYPE
			SYNTAX INTEGER
				{
				autoConnect(0),
				flowConnect(1)
				}
			MAX-ACCESS read-write
			STATUS current
			DESCRIPTION
				"Description."
			::= { priWanConnV6CfgEntry 30 }

		
--  1.3.6.1.4.1.37950.1.1.6.1.8.20.1.31
		-- 1.3.6.1.4.1.37950.1.1.6.1.8.20.1.31
		priV6ConnCfgDhcpv6ClientAddressS OBJECT-TYPE
			SYNTAX INTEGER
				{
				disable(0),
				enable(1)
				}
			MAX-ACCESS read-write
			STATUS current
			DESCRIPTION
				"Description."
			::= { priWanConnV6CfgEntry 31 }

		
--  1.3.6.1.4.1.37950.1.1.6.1.8.20.1.32
		-- 1.3.6.1.4.1.37950.1.1.6.1.8.20.1.32
		priV6ConnCfgDhcpv6ClientPrefixS OBJECT-TYPE
			SYNTAX INTEGER
				{
				disable(0),
				enable(1)
				}
			MAX-ACCESS read-write
			STATUS current
			DESCRIPTION
				"Description."
			::= { priWanConnV6CfgEntry 32 }

		
--  1.3.6.1.4.1.37950.1.1.6.1.8.20.1.33
		-- 1.3.6.1.4.1.37950.1.1.6.1.8.20.1.33
		priV6ConnCfgDsLiteEnableS OBJECT-TYPE
			SYNTAX INTEGER
				{
				disable(0),
				enable(1)
				}
			MAX-ACCESS read-write
			STATUS current
			DESCRIPTION
				"Description."
			::= { priWanConnV6CfgEntry 33 }

		
--  1.3.6.1.4.1.37950.1.1.6.1.8.20.1.34
		-- 1.3.6.1.4.1.37950.1.1.6.1.8.20.1.34
		priV6ConnCfgDsLiteAftrModeS OBJECT-TYPE
			SYNTAX INTEGER
				{
				dhcpv6(0),
				manual(1)
				}
			MAX-ACCESS read-write
			STATUS current
			DESCRIPTION
				"Description."
			::= { priWanConnV6CfgEntry 34 }

		
--  1.3.6.1.4.1.37950.1.1.6.1.8.20.1.35
		-- 1.3.6.1.4.1.37950.1.1.6.1.8.20.1.35
		priV6ConnCfgDsLiteAddressTypeS OBJECT-TYPE
			SYNTAX INTEGER
				{
				ipv6(0),
				dns(1)
				}
			MAX-ACCESS read-write
			STATUS current
			DESCRIPTION
				"Description."
			::= { priWanConnV6CfgEntry 35 }

		
--  1.3.6.1.4.1.37950.1.1.6.1.8.20.1.36
		-- 1.3.6.1.4.1.37950.1.1.6.1.8.20.1.36
		priV6ConnCfgDsLiteAddressS OBJECT-TYPE
			SYNTAX OCTET STRING
			MAX-ACCESS read-write
			STATUS current
			DESCRIPTION
				"Description."
			::= { priWanConnV6CfgEntry 36 }

		
--  1.3.6.1.4.1.37950.1.1.6.1.8.20.1.37
		-- 1.3.6.1.4.1.37950.1.1.6.1.8.20.1.37
		priv6ConnCfgQosEnableS OBJECT-TYPE
			SYNTAX INTEGER
				{
				disable(0),
				enable(1)
				}
			MAX-ACCESS read-write
			STATUS current
			DESCRIPTION
				"Description."
			::= { priWanConnV6CfgEntry 37 }

		
--  1.3.6.1.4.1.37950.1.1.6.1.8.20.1.38
		-- 1.3.6.1.4.1.37950.1.1.6.1.8.20.1.38
		priV6ConnCfgVlanModeS OBJECT-TYPE
			SYNTAX INTEGER
				{
				disable(0),
				tag(1),
				transparent(2)
				}
			MAX-ACCESS read-write
			STATUS current
			DESCRIPTION
				"Description."
			::= { priWanConnV6CfgEntry 38 }

		
--  1.3.6.1.4.1.37950.1.1.6.1.8.20.1.39
		-- 1.3.6.1.4.1.37950.1.1.6.1.8.20.1.39
		priV6ConnCfgTranslationEnableS OBJECT-TYPE
			SYNTAX INTEGER
				{
				disable(0),
				enable(1)
				}
			MAX-ACCESS read-write
			STATUS current
			DESCRIPTION
				"Description."
			::= { priWanConnV6CfgEntry 39 }

		
--  1.3.6.1.4.1.37950.1.1.6.1.8.20.1.40
		-- 1.3.6.1.4.1.37950.1.1.6.1.8.20.1.40
		priV6ConnCfgTranslationVlanS OBJECT-TYPE
			SYNTAX INTEGER (1..4095)
			MAX-ACCESS read-write
			STATUS current
			DESCRIPTION
				"Description."
			::= { priWanConnV6CfgEntry 40 }

		
--  1.3.6.1.4.1.37950.1.1.6.1.8.20.1.41
		-- 1.3.6.1.4.1.37950.1.1.6.1.8.20.1.41
		priV6ConnCfgTranslationCosS OBJECT-TYPE
			SYNTAX INTEGER (0..7)
			MAX-ACCESS read-write
			STATUS current
			DESCRIPTION
				"Description."
			::= { priWanConnV6CfgEntry 41 }

		
--  1.3.6.1.4.1.37950.1.1.6.1.8.20.1.42
		-- 1.3.6.1.4.1.37950.1.1.6.1.8.20.1.42
		priV6ConnCfgQinqEnableS OBJECT-TYPE
			SYNTAX INTEGER
				{
				disable(0),
				enable(1)
				}
			MAX-ACCESS read-write
			STATUS current
			DESCRIPTION
				"Description."
			::= { priWanConnV6CfgEntry 42 }

		
--  1.3.6.1.4.1.37950.1.1.6.1.8.20.1.43
		-- 1.3.6.1.4.1.37950.1.1.6.1.8.20.1.43
		priV6ConnCfgQinqTpidS OBJECT-TYPE
			SYNTAX INTEGER (1..65534)
			MAX-ACCESS read-write
			STATUS current
			DESCRIPTION
				"Description."
			::= { priWanConnV6CfgEntry 43 }

		
--  1.3.6.1.4.1.37950.1.1.6.1.8.20.1.44
		-- 1.3.6.1.4.1.37950.1.1.6.1.8.20.1.44
		priV6ConnCfgSvlanIdS OBJECT-TYPE
			SYNTAX INTEGER (1..4095)
			MAX-ACCESS read-write
			STATUS current
			DESCRIPTION
				"Description."
			::= { priWanConnV6CfgEntry 44 }

		
--  1.3.6.1.4.1.37950.1.1.6.1.8.20.1.45
		-- 1.3.6.1.4.1.37950.1.1.6.1.8.20.1.45
		priV6ConnCfgSvlanCosS OBJECT-TYPE
			SYNTAX INTEGER (0..7)
			MAX-ACCESS read-write
			STATUS current
			DESCRIPTION
				"Description."
			::= { priWanConnV6CfgEntry 45 }

		
--  1.3.6.1.4.1.37950.1.1.6.1.8.20.1.46
		-- 1.3.6.1.4.1.37950.1.1.6.1.8.20.1.46
		priV6ConnCfgRouteMtuS OBJECT-TYPE
			SYNTAX Integer32 (0 | 576..1500)
			MAX-ACCESS read-write
			STATUS current
			DESCRIPTION
				"Description."
			::= { priWanConnV6CfgEntry 46 }

		
--  1.3.6.1.4.1.37950.1.1.6.1.8.21
		-- 1.3.6.1.4.1.37950.1.1.6.1.8.21
		priDhcpServerV6Table OBJECT-TYPE
			SYNTAX SEQUENCE OF PriDhcpServerV6Entry
			MAX-ACCESS not-accessible
			STATUS current
			DESCRIPTION
				"Description."
			::= { gOnuPriCfgInfo 21 }

		
--  1.3.6.1.4.1.37950.1.1.6.1.8.21.1
		-- 1.3.6.1.4.1.37950.1.1.6.1.8.21.1
		priDhcpServerV6Entry OBJECT-TYPE
			SYNTAX PriDhcpServerV6Entry
			MAX-ACCESS not-accessible
			STATUS current
			DESCRIPTION
				"Description."
			INDEX { priDhcpv6ServerPon, priDhcpv6ServerOnu }
			::= { priDhcpServerV6Table 1 }

		
		PriDhcpServerV6Entry ::=
			SEQUENCE { 
				priDhcpv6ServerPon
					Integer32,
				priDhcpv6ServerOnu
					Integer32,
				priDhcpv6LanIp
					OCTET STRING,
				priDhcpv6LanPrefixlen
					INTEGER,
				priDhcpv6PrefixMode
					INTEGER,
				priDhcpv6PrefixModeIp
					OCTET STRING,
				priDhcpv6Enable
					INTEGER,
				priDhcpv6Preference
					Unsigned32,
				priDhcpv6BeginIp
					OCTET STRING,
				priDhcpv6EndIp
					OCTET STRING,
				priDhcpv6PoolType
					INTEGER,
				priDhcpv6MasterDns
					OCTET STRING,
				priDhcpv6SlaveDns
					OCTET STRING,
				priDhcpv6Gateway
					OCTET STRING,
				priDhcpv6RelayIp
					OCTET STRING,
				priDhcpv6RA
					INTEGER,
				priDhcpv6RAManage
					INTEGER,
				priDhcpv6RAOther
					INTEGER,
				priDhcpv6RAMaxInterval
					Integer32,
				priDhcpv6RAMinInterval
					Integer32,
				priDhcpv6Valid
					Unsigned32,
				priDhcpv6PrefixModeWanIndex
					Integer32,
				priDhcpv6SupportWanIndex
					OCTET STRING,
				priDhcpv6DNSMode
					INTEGER,
				priDhcpv6DNSModeWanIndex
					Integer32
			 }

--  1.3.6.1.4.1.37950.1.1.6.1.8.21.1.1
		-- 1.3.6.1.4.1.37950.1.1.6.1.8.21.1.1
		priDhcpv6ServerPon OBJECT-TYPE
			SYNTAX Integer32
			MAX-ACCESS read-write
			STATUS current
			DESCRIPTION
				"Description."
			::= { priDhcpServerV6Entry 1 }

		
--  1.3.6.1.4.1.37950.1.1.6.1.8.21.1.2
		-- 1.3.6.1.4.1.37950.1.1.6.1.8.21.1.2
		priDhcpv6ServerOnu OBJECT-TYPE
			SYNTAX Integer32
			MAX-ACCESS read-write
			STATUS current
			DESCRIPTION
				"Description."
			::= { priDhcpServerV6Entry 2 }

		
--  1.3.6.1.4.1.37950.1.1.6.1.8.21.1.3
		-- 1.3.6.1.4.1.37950.1.1.6.1.8.21.1.3
		priDhcpv6LanIp OBJECT-TYPE
			SYNTAX OCTET STRING
			MAX-ACCESS read-write
			STATUS current
			DESCRIPTION
				"Description."
			::= { priDhcpServerV6Entry 3 }

		
--  1.3.6.1.4.1.37950.1.1.6.1.8.21.1.4
		-- 1.3.6.1.4.1.37950.1.1.6.1.8.21.1.4
		priDhcpv6LanPrefixlen OBJECT-TYPE
			SYNTAX INTEGER
			MAX-ACCESS read-write
			STATUS current
			DESCRIPTION
				"Description."
			::= { priDhcpServerV6Entry 4 }

		
--  1.3.6.1.4.1.37950.1.1.6.1.8.21.1.5
		-- 1.3.6.1.4.1.37950.1.1.6.1.8.21.1.5
		priDhcpv6PrefixMode OBJECT-TYPE
			SYNTAX INTEGER
				{
				wan_delegated(0),
				static(1),
				auto(2)
				}
			MAX-ACCESS read-write
			STATUS current
			DESCRIPTION
				"Description."
			::= { priDhcpServerV6Entry 5 }

		
--  1.3.6.1.4.1.37950.1.1.6.1.8.21.1.6
		-- 1.3.6.1.4.1.37950.1.1.6.1.8.21.1.6
		priDhcpv6PrefixModeIp OBJECT-TYPE
			SYNTAX OCTET STRING
			MAX-ACCESS read-write
			STATUS current
			DESCRIPTION
				"Description."
			::= { priDhcpServerV6Entry 6 }

		
--  1.3.6.1.4.1.37950.1.1.6.1.8.21.1.7
		-- 1.3.6.1.4.1.37950.1.1.6.1.8.21.1.7
		priDhcpv6Enable OBJECT-TYPE
			SYNTAX INTEGER
				{
				disable(0),
				enable(1),
				relay(2)
				}
			MAX-ACCESS read-write
			STATUS current
			DESCRIPTION
				"Description."
			::= { priDhcpServerV6Entry 7 }

		
--  1.3.6.1.4.1.37950.1.1.6.1.8.21.1.8
		-- 1.3.6.1.4.1.37950.1.1.6.1.8.21.1.8
		priDhcpv6Preference OBJECT-TYPE
			SYNTAX Unsigned32
			MAX-ACCESS read-write
			STATUS current
			DESCRIPTION
				"Description."
			::= { priDhcpServerV6Entry 8 }

		
--  1.3.6.1.4.1.37950.1.1.6.1.8.21.1.9
		-- 1.3.6.1.4.1.37950.1.1.6.1.8.21.1.9
		priDhcpv6BeginIp OBJECT-TYPE
			SYNTAX OCTET STRING
			MAX-ACCESS read-write
			STATUS current
			DESCRIPTION
				"Description."
			::= { priDhcpServerV6Entry 9 }

		
--  1.3.6.1.4.1.37950.1.1.6.1.8.21.1.10
		-- 1.3.6.1.4.1.37950.1.1.6.1.8.21.1.10
		priDhcpv6EndIp OBJECT-TYPE
			SYNTAX OCTET STRING
			MAX-ACCESS read-write
			STATUS current
			DESCRIPTION
				"Description."
			::= { priDhcpServerV6Entry 10 }

		
--  1.3.6.1.4.1.37950.1.1.6.1.8.21.1.11
		-- 1.3.6.1.4.1.37950.1.1.6.1.8.21.1.11
		priDhcpv6PoolType OBJECT-TYPE
			SYNTAX INTEGER
				{
				pc(0),
				camera(1),
				stb(2),
				ip_phone(3)
				}
			MAX-ACCESS read-write
			STATUS current
			DESCRIPTION
				"Description."
			::= { priDhcpServerV6Entry 11 }

		
--  1.3.6.1.4.1.37950.1.1.6.1.8.21.1.12
		-- 1.3.6.1.4.1.37950.1.1.6.1.8.21.1.12
		priDhcpv6MasterDns OBJECT-TYPE
			SYNTAX OCTET STRING
			MAX-ACCESS read-write
			STATUS current
			DESCRIPTION
				"Description."
			::= { priDhcpServerV6Entry 12 }

		
--  1.3.6.1.4.1.37950.1.1.6.1.8.21.1.13
		-- 1.3.6.1.4.1.37950.1.1.6.1.8.21.1.13
		priDhcpv6SlaveDns OBJECT-TYPE
			SYNTAX OCTET STRING
			MAX-ACCESS read-write
			STATUS current
			DESCRIPTION
				"Description."
			::= { priDhcpServerV6Entry 13 }

		
--  1.3.6.1.4.1.37950.1.1.6.1.8.21.1.14
		-- 1.3.6.1.4.1.37950.1.1.6.1.8.21.1.14
		priDhcpv6Gateway OBJECT-TYPE
			SYNTAX OCTET STRING
			MAX-ACCESS read-write
			STATUS current
			DESCRIPTION
				"Description."
			::= { priDhcpServerV6Entry 14 }

		
--  1.3.6.1.4.1.37950.1.1.6.1.8.21.1.15
		-- 1.3.6.1.4.1.37950.1.1.6.1.8.21.1.15
		priDhcpv6RelayIp OBJECT-TYPE
			SYNTAX OCTET STRING
			MAX-ACCESS read-write
			STATUS current
			DESCRIPTION
				"Description."
			::= { priDhcpServerV6Entry 15 }

		
--  1.3.6.1.4.1.37950.1.1.6.1.8.21.1.16
		-- 1.3.6.1.4.1.37950.1.1.6.1.8.21.1.16
		priDhcpv6RA OBJECT-TYPE
			SYNTAX INTEGER
				{
				disable(0),
				enable(1)
				}
			MAX-ACCESS read-write
			STATUS current
			DESCRIPTION
				"Description."
			::= { priDhcpServerV6Entry 16 }

		
--  1.3.6.1.4.1.37950.1.1.6.1.8.21.1.17
		-- 1.3.6.1.4.1.37950.1.1.6.1.8.21.1.17
		priDhcpv6RAManage OBJECT-TYPE
			SYNTAX INTEGER
				{
				disable(0),
				enable(1)
				}
			MAX-ACCESS read-write
			STATUS current
			DESCRIPTION
				"Description."
			::= { priDhcpServerV6Entry 17 }

		
--  1.3.6.1.4.1.37950.1.1.6.1.8.21.1.18
		-- 1.3.6.1.4.1.37950.1.1.6.1.8.21.1.18
		priDhcpv6RAOther OBJECT-TYPE
			SYNTAX INTEGER
				{
				disable(0),
				enable(1)
				}
			MAX-ACCESS read-write
			STATUS current
			DESCRIPTION
				"Description."
			::= { priDhcpServerV6Entry 18 }

		
--  1.3.6.1.4.1.37950.1.1.6.1.8.21.1.19
		-- 1.3.6.1.4.1.37950.1.1.6.1.8.21.1.19
		priDhcpv6RAMaxInterval OBJECT-TYPE
			SYNTAX Integer32
			MAX-ACCESS read-write
			STATUS current
			DESCRIPTION
				"Description."
			::= { priDhcpServerV6Entry 19 }

		
--  1.3.6.1.4.1.37950.1.1.6.1.8.21.1.20
		-- 1.3.6.1.4.1.37950.1.1.6.1.8.21.1.20
		priDhcpv6RAMinInterval OBJECT-TYPE
			SYNTAX Integer32
			MAX-ACCESS read-write
			STATUS current
			DESCRIPTION
				"Description."
			::= { priDhcpServerV6Entry 20 }

		
--  1.3.6.1.4.1.37950.1.1.6.1.8.21.1.21
		-- 1.3.6.1.4.1.37950.1.1.6.1.8.21.1.21
		priDhcpv6Valid OBJECT-TYPE
			SYNTAX Unsigned32
			MAX-ACCESS read-write
			STATUS current
			DESCRIPTION
				"Description."
			::= { priDhcpServerV6Entry 21 }

		
--  1.3.6.1.4.1.37950.1.1.6.1.8.21.1.22
		-- 1.3.6.1.4.1.37950.1.1.6.1.8.21.1.22
		priDhcpv6PrefixModeWanIndex OBJECT-TYPE
			SYNTAX Integer32
			MAX-ACCESS read-write
			STATUS current
			DESCRIPTION
				"Description."
			::= { priDhcpServerV6Entry 22 }

		
--  1.3.6.1.4.1.37950.1.1.6.1.8.21.1.23
		-- 1.3.6.1.4.1.37950.1.1.6.1.8.21.1.23
		priDhcpv6SupportWanIndex OBJECT-TYPE
			SYNTAX OCTET STRING
			MAX-ACCESS read-write
			STATUS current
			DESCRIPTION
				"Description."
			::= { priDhcpServerV6Entry 23 }

		
--  1.3.6.1.4.1.37950.1.1.6.1.8.21.1.24
		-- 1.3.6.1.4.1.37950.1.1.6.1.8.21.1.24
		priDhcpv6DNSMode OBJECT-TYPE
			SYNTAX INTEGER
				{
				wanconnection(0),
				static(1),
				hgwproxy(2)
				}
			MAX-ACCESS read-write
			STATUS current
			DESCRIPTION
				"Description."
			::= { priDhcpServerV6Entry 24 }

		
--  1.3.6.1.4.1.37950.1.1.6.1.8.21.1.25
		-- 1.3.6.1.4.1.37950.1.1.6.1.8.21.1.25
		priDhcpv6DNSModeWanIndex OBJECT-TYPE
			SYNTAX Integer32
			MAX-ACCESS read-write
			STATUS current
			DESCRIPTION
				"Description."
			::= { priDhcpServerV6Entry 25 }

		
--  1.3.6.1.4.1.37950.1.1.6.1.8.22
		-- 1.3.6.1.4.1.37950.1.1.6.1.8.22
		priLoopChkTable OBJECT-TYPE
			SYNTAX SEQUENCE OF PriLoopChkEntry
			MAX-ACCESS not-accessible
			STATUS current
			DESCRIPTION
				"Description."
			::= { gOnuPriCfgInfo 22 }

		
--  1.3.6.1.4.1.37950.1.1.6.1.8.22.1
		-- 1.3.6.1.4.1.37950.1.1.6.1.8.22.1
		priLoopChkEntry OBJECT-TYPE
			SYNTAX PriLoopChkEntry
			MAX-ACCESS not-accessible
			STATUS current
			DESCRIPTION
				"Description."
			INDEX { gOnuPriLCPonS, gOnuPriLCOnuS }
			::= { priLoopChkTable 1 }

		
		PriLoopChkEntry ::=
			SEQUENCE { 
				gOnuPriLCPonS
					Integer32,
				gOnuPriLCOnuS
					Integer32,
				gOnuPriLCStatusS
					INTEGER,
				gOnuPriLCCheckIntervalS
					Integer32,
				gOnuPriLCRecoverIntervalS
					Integer32,
				gOnuPriLCEthernetTypeS
					OCTET STRING,
				gOnuPriLCVlanS
					Integer32,
				gOnuPriLCDestMacTypeS
					INTEGER,
				gOnuPriLCPortClosingTimeS
					Integer32,
				gOnuPriLCAlarmS
					INTEGER,
				gOnuPriLCPortdisloopedS
					INTEGER
			 }

--  1.3.6.1.4.1.37950.1.1.6.1.8.22.1.1
		-- 1.3.6.1.4.1.37950.1.1.6.1.8.22.1.1
		gOnuPriLCPonS OBJECT-TYPE
			SYNTAX Integer32
			MAX-ACCESS read-write
			STATUS current
			DESCRIPTION
				"Description."
			::= { priLoopChkEntry 1 }

		
--  1.3.6.1.4.1.37950.1.1.6.1.8.22.1.2
		-- 1.3.6.1.4.1.37950.1.1.6.1.8.22.1.2
		gOnuPriLCOnuS OBJECT-TYPE
			SYNTAX Integer32
			MAX-ACCESS read-write
			STATUS current
			DESCRIPTION
				"Description."
			::= { priLoopChkEntry 2 }

		
--  1.3.6.1.4.1.37950.1.1.6.1.8.22.1.3
		-- 1.3.6.1.4.1.37950.1.1.6.1.8.22.1.3
		gOnuPriLCStatusS OBJECT-TYPE
			SYNTAX INTEGER
				{
				disable(0),
				enable(1)
				}
			MAX-ACCESS read-write
			STATUS current
			DESCRIPTION
				"Description."
			::= { priLoopChkEntry 3 }

		
--  1.3.6.1.4.1.37950.1.1.6.1.8.22.1.4
		-- 1.3.6.1.4.1.37950.1.1.6.1.8.22.1.4
		gOnuPriLCCheckIntervalS OBJECT-TYPE
			SYNTAX Integer32
			MAX-ACCESS read-write
			STATUS current
			DESCRIPTION
				"Description."
			::= { priLoopChkEntry 4 }

		
--  1.3.6.1.4.1.37950.1.1.6.1.8.22.1.5
		-- 1.3.6.1.4.1.37950.1.1.6.1.8.22.1.5
		gOnuPriLCRecoverIntervalS OBJECT-TYPE
			SYNTAX Integer32
			MAX-ACCESS read-write
			STATUS current
			DESCRIPTION
				"Description."
			::= { priLoopChkEntry 5 }

		
--  1.3.6.1.4.1.37950.1.1.6.1.8.22.1.6
		-- 1.3.6.1.4.1.37950.1.1.6.1.8.22.1.6
		gOnuPriLCEthernetTypeS OBJECT-TYPE
			SYNTAX OCTET STRING
			MAX-ACCESS read-write
			STATUS current
			DESCRIPTION
				"Description."
			::= { priLoopChkEntry 6 }

		
--  1.3.6.1.4.1.37950.1.1.6.1.8.22.1.7
		-- 1.3.6.1.4.1.37950.1.1.6.1.8.22.1.7
		gOnuPriLCVlanS OBJECT-TYPE
			SYNTAX Integer32
			MAX-ACCESS read-write
			STATUS current
			DESCRIPTION
				"Description."
			::= { priLoopChkEntry 7 }

		
--  1.3.6.1.4.1.37950.1.1.6.1.8.22.1.8
		-- 1.3.6.1.4.1.37950.1.1.6.1.8.22.1.8
		gOnuPriLCDestMacTypeS OBJECT-TYPE
			SYNTAX INTEGER
				{
				broadcast_address(0),
				bpdu_address(1)
				}
			MAX-ACCESS read-write
			STATUS current
			DESCRIPTION
				"Description."
			::= { priLoopChkEntry 8 }

		
--  1.3.6.1.4.1.37950.1.1.6.1.8.22.1.9
		-- 1.3.6.1.4.1.37950.1.1.6.1.8.22.1.9
		gOnuPriLCPortClosingTimeS OBJECT-TYPE
			SYNTAX Integer32
			MAX-ACCESS read-write
			STATUS current
			DESCRIPTION
				"Description."
			::= { priLoopChkEntry 9 }

		
--  1.3.6.1.4.1.37950.1.1.6.1.8.22.1.10
		-- 1.3.6.1.4.1.37950.1.1.6.1.8.22.1.10
		gOnuPriLCAlarmS OBJECT-TYPE
			SYNTAX INTEGER
				{
				disable(0),
				enable(1)
				}
			MAX-ACCESS read-write
			STATUS current
			DESCRIPTION
				"Description."
			::= { priLoopChkEntry 10 }

		
--  1.3.6.1.4.1.37950.1.1.6.1.8.22.1.11
		-- 1.3.6.1.4.1.37950.1.1.6.1.8.22.1.11
		gOnuPriLCPortdisloopedS OBJECT-TYPE
			SYNTAX INTEGER
				{
				disable(0),
				enable(1)
				}
			MAX-ACCESS read-write
			STATUS current
			DESCRIPTION
				"Description."
			::= { priLoopChkEntry 11 }

		
--  1.3.6.1.4.1.37950.1.1.6.1.8.23
		-- 1.3.6.1.4.1.37950.1.1.6.1.8.23
		priTr069ManageTable OBJECT-TYPE
			SYNTAX SEQUENCE OF PriTr069ManageEntry
			MAX-ACCESS not-accessible
			STATUS current
			DESCRIPTION
				"Description."
			::= { gOnuPriCfgInfo 23 }

		
--  1.3.6.1.4.1.37950.1.1.6.1.8.23.1
		-- 1.3.6.1.4.1.37950.1.1.6.1.8.23.1
		priTr069ManageEntry OBJECT-TYPE
			SYNTAX PriTr069ManageEntry
			MAX-ACCESS not-accessible
			STATUS current
			DESCRIPTION
				"Description."
			INDEX { priMngPon, priMngOnu }
			::= { priTr069ManageTable 1 }

		
		PriTr069ManageEntry ::=
			SEQUENCE { 
				priMngPon
					Integer32,
				priMngOnu
					Integer32,
				priMngAcsAddressS
					OCTET STRING,
				priMngAcsUsernameS
					OCTET STRING,
				priMngAcsPasswordS
					OCTET STRING,
				priMngCertificateEnS
					INTEGER,
				priMngInformEnS
					INTEGER,
				priMngInformIntervalTimeS
					Unsigned32,
				priMngRevConnUsernameS
					OCTET STRING,
				priMngRevConnPasswordS
					OCTET STRING,
				priMngStatusS
					INTEGER,
				priMngIDS
					OCTET STRING
			 }

--  1.3.6.1.4.1.37950.1.1.6.1.8.23.1.1
		-- 1.3.6.1.4.1.37950.1.1.6.1.8.23.1.1
		priMngPon OBJECT-TYPE
			SYNTAX Integer32
			MAX-ACCESS read-only
			STATUS current
			DESCRIPTION
				"Description."
			::= { priTr069ManageEntry 1 }

		
--  1.3.6.1.4.1.37950.1.1.6.1.8.23.1.2
		-- 1.3.6.1.4.1.37950.1.1.6.1.8.23.1.2
		priMngOnu OBJECT-TYPE
			SYNTAX Integer32
			MAX-ACCESS read-only
			STATUS current
			DESCRIPTION
				"Description."
			::= { priTr069ManageEntry 2 }

		
--  1.3.6.1.4.1.37950.1.1.6.1.8.23.1.3
		-- 1.3.6.1.4.1.37950.1.1.6.1.8.23.1.3
		priMngAcsAddressS OBJECT-TYPE
			SYNTAX OCTET STRING
			MAX-ACCESS read-only
			STATUS current
			DESCRIPTION
				"Description."
			::= { priTr069ManageEntry 3 }

		
--  1.3.6.1.4.1.37950.1.1.6.1.8.23.1.4
		-- 1.3.6.1.4.1.37950.1.1.6.1.8.23.1.4
		priMngAcsUsernameS OBJECT-TYPE
			SYNTAX OCTET STRING
			MAX-ACCESS read-only
			STATUS current
			DESCRIPTION
				"Description."
			::= { priTr069ManageEntry 4 }

		
--  1.3.6.1.4.1.37950.1.1.6.1.8.23.1.5
		-- 1.3.6.1.4.1.37950.1.1.6.1.8.23.1.5
		priMngAcsPasswordS OBJECT-TYPE
			SYNTAX OCTET STRING
			MAX-ACCESS read-only
			STATUS current
			DESCRIPTION
				"Description."
			::= { priTr069ManageEntry 5 }

		
--  1.3.6.1.4.1.37950.1.1.6.1.8.23.1.6
		-- 1.3.6.1.4.1.37950.1.1.6.1.8.23.1.6
		priMngCertificateEnS OBJECT-TYPE
			SYNTAX INTEGER
				{
				disable(0),
				enable(1)
				}
			MAX-ACCESS read-only
			STATUS current
			DESCRIPTION
				"Description."
			::= { priTr069ManageEntry 6 }

		
--  1.3.6.1.4.1.37950.1.1.6.1.8.23.1.7
		-- 1.3.6.1.4.1.37950.1.1.6.1.8.23.1.7
		priMngInformEnS OBJECT-TYPE
			SYNTAX INTEGER
				{
				disable(0),
				enable(1)
				}
			MAX-ACCESS read-only
			STATUS current
			DESCRIPTION
				"Description."
			::= { priTr069ManageEntry 7 }

		
--  1.3.6.1.4.1.37950.1.1.6.1.8.23.1.8
		-- 1.3.6.1.4.1.37950.1.1.6.1.8.23.1.8
		priMngInformIntervalTimeS OBJECT-TYPE
			SYNTAX Unsigned32 (0..4294967295)
			MAX-ACCESS read-only
			STATUS current
			DESCRIPTION
				"Description."
			::= { priTr069ManageEntry 8 }

		
--  1.3.6.1.4.1.37950.1.1.6.1.8.23.1.9
		-- 1.3.6.1.4.1.37950.1.1.6.1.8.23.1.9
		priMngRevConnUsernameS OBJECT-TYPE
			SYNTAX OCTET STRING
			MAX-ACCESS read-only
			STATUS current
			DESCRIPTION
				"Description."
			::= { priTr069ManageEntry 9 }

		
--  1.3.6.1.4.1.37950.1.1.6.1.8.23.1.10
		-- 1.3.6.1.4.1.37950.1.1.6.1.8.23.1.10
		priMngRevConnPasswordS OBJECT-TYPE
			SYNTAX OCTET STRING
			MAX-ACCESS read-only
			STATUS current
			DESCRIPTION
				"Description."
			::= { priTr069ManageEntry 10 }

		
--  1.3.6.1.4.1.37950.1.1.6.1.8.23.1.11
		-- 1.3.6.1.4.1.37950.1.1.6.1.8.23.1.11
		priMngStatusS OBJECT-TYPE
			SYNTAX INTEGER
				{
				disable(0),
				enable(1)
				}
			MAX-ACCESS read-only
			STATUS current
			DESCRIPTION
				"Description."
			::= { priTr069ManageEntry 11 }

		
--  1.3.6.1.4.1.37950.1.1.6.1.8.23.1.12
		-- 1.3.6.1.4.1.37950.1.1.6.1.8.23.1.12
		priMngIDS OBJECT-TYPE
			SYNTAX OCTET STRING
			MAX-ACCESS read-write
			STATUS current
			DESCRIPTION
				"Description."
			::= { priTr069ManageEntry 12 }

		
--  1.3.6.1.4.1.37950.1.1.6.1.8.24
		-- 1.3.6.1.4.1.37950.1.1.6.1.8.24
		priTr069StunTable OBJECT-TYPE
			SYNTAX SEQUENCE OF PriTr069StunEntry
			MAX-ACCESS not-accessible
			STATUS current
			DESCRIPTION
				"Description."
			::= { gOnuPriCfgInfo 24 }

		
--  1.3.6.1.4.1.37950.1.1.6.1.8.24.1
		-- 1.3.6.1.4.1.37950.1.1.6.1.8.24.1
		priTr069StunEntry OBJECT-TYPE
			SYNTAX PriTr069StunEntry
			MAX-ACCESS not-accessible
			STATUS current
			DESCRIPTION
				"Description."
			INDEX { priStunPon, priStunOnu }
			::= { priTr069StunTable 1 }

		
		PriTr069StunEntry ::=
			SEQUENCE { 
				priStunPon
					Integer32,
				priStunOnu
					Integer32,
				priStunAddressS
					OCTET STRING,
				priStunPortS
					Integer32,
				priStunUsernameS
					OCTET STRING,
				priStunPasswordS
					OCTET STRING,
				priStunStatusS
					INTEGER
			 }

--  1.3.6.1.4.1.37950.1.1.6.1.8.24.1.1
		-- 1.3.6.1.4.1.37950.1.1.6.1.8.24.1.1
		priStunPon OBJECT-TYPE
			SYNTAX Integer32
			MAX-ACCESS read-only
			STATUS current
			DESCRIPTION
				"Description."
			::= { priTr069StunEntry 1 }

		
--  1.3.6.1.4.1.37950.1.1.6.1.8.24.1.2
		-- 1.3.6.1.4.1.37950.1.1.6.1.8.24.1.2
		priStunOnu OBJECT-TYPE
			SYNTAX Integer32
			MAX-ACCESS read-only
			STATUS current
			DESCRIPTION
				"Description."
			::= { priTr069StunEntry 2 }

		
--  1.3.6.1.4.1.37950.1.1.6.1.8.24.1.3
		-- 1.3.6.1.4.1.37950.1.1.6.1.8.24.1.3
		priStunAddressS OBJECT-TYPE
			SYNTAX OCTET STRING
			MAX-ACCESS read-only
			STATUS current
			DESCRIPTION
				"Description."
			::= { priTr069StunEntry 3 }

		
--  1.3.6.1.4.1.37950.1.1.6.1.8.24.1.4
		-- 1.3.6.1.4.1.37950.1.1.6.1.8.24.1.4
		priStunPortS OBJECT-TYPE
			SYNTAX Integer32 (1..65535)
			MAX-ACCESS read-only
			STATUS current
			DESCRIPTION
				"Description."
			::= { priTr069StunEntry 4 }

		
--  1.3.6.1.4.1.37950.1.1.6.1.8.24.1.5
		-- 1.3.6.1.4.1.37950.1.1.6.1.8.24.1.5
		priStunUsernameS OBJECT-TYPE
			SYNTAX OCTET STRING
			MAX-ACCESS read-only
			STATUS current
			DESCRIPTION
				"Description."
			::= { priTr069StunEntry 5 }

		
--  1.3.6.1.4.1.37950.1.1.6.1.8.24.1.6
		-- 1.3.6.1.4.1.37950.1.1.6.1.8.24.1.6
		priStunPasswordS OBJECT-TYPE
			SYNTAX OCTET STRING
			MAX-ACCESS read-only
			STATUS current
			DESCRIPTION
				"Description."
			::= { priTr069StunEntry 6 }

		
--  1.3.6.1.4.1.37950.1.1.6.1.8.24.1.7
		-- 1.3.6.1.4.1.37950.1.1.6.1.8.24.1.7
		priStunStatusS OBJECT-TYPE
			SYNTAX INTEGER
				{
				disable(0),
				enable(1)
				}
			MAX-ACCESS read-only
			STATUS current
			DESCRIPTION
				"Description."
			::= { priTr069StunEntry 7 }

		
--    1.3.6.1.4.1.37950.1.1.5.12.3.2.7
-- 1.3.6.1.4.1.37950.1.1.5.12.3.2.7
-- 1.3.6.1.4.1.37950.1.1.6.1.8.25
		-- 1.3.6.1.4.1.37950.1.1.6.1.8.25
		priNatTypeTable OBJECT-TYPE
			SYNTAX SEQUENCE OF PriNatTypeEntry
			MAX-ACCESS not-accessible
			STATUS current
			DESCRIPTION
				"Description."
			::= { gOnuPriCfgInfo 25 }

		
--     1.3.6.1.4.1.37950.1.1.5.12.3.2.7.1
-- 1.3.6.1.4.1.37950.1.1.5.12.3.2.7.1
-- 1.3.6.1.4.1.37950.1.1.5.12.3.2.7.1
-- 1.3.6.1.4.1.37950.1.1.6.1.8.25.1
		-- 1.3.6.1.4.1.37950.1.1.6.1.8.25.1
		priNatTypeEntry OBJECT-TYPE
			SYNTAX PriNatTypeEntry
			MAX-ACCESS not-accessible
			STATUS current
			DESCRIPTION
				"Description."
			INDEX { priNatTypePonIDS, priNatTypeOnuIDS }
			::= { priNatTypeTable 1 }

		
		PriNatTypeEntry ::=
			SEQUENCE { 
				priNatTypePonIDS
					INTEGER,
				priNatTypeOnuIDS
					INTEGER,
				priNatTypeS
					INTEGER
			 }

--     1.3.6.1.4.1.37950.1.1.5.12.3.2.7.1.1
-- 1.3.6.1.4.1.37950.1.1.5.12.3.2.7.1.1
-- 1.3.6.1.4.1.37950.1.1.5.12.3.2.7.1.1
-- 1.3.6.1.4.1.37950.1.1.6.1.8.25.1.1
		-- 1.3.6.1.4.1.37950.1.1.6.1.8.25.1.1
		priNatTypePonIDS OBJECT-TYPE
			SYNTAX INTEGER (1..16)
			MAX-ACCESS read-write
			STATUS current
			DESCRIPTION
				"Description."
			::= { priNatTypeEntry 1 }

		
--     1.3.6.1.4.1.37950.1.1.5.12.3.2.7.1.2
-- 1.3.6.1.4.1.37950.1.1.5.12.3.2.7.1.2
-- 1.3.6.1.4.1.37950.1.1.5.12.3.2.7.1.2
-- 1.3.6.1.4.1.37950.1.1.6.1.8.25.1.2
		-- 1.3.6.1.4.1.37950.1.1.6.1.8.25.1.2
		priNatTypeOnuIDS OBJECT-TYPE
			SYNTAX INTEGER (1..65535)
			MAX-ACCESS read-write
			STATUS current
			DESCRIPTION
				"Description."
			::= { priNatTypeEntry 2 }

		
--     1.3.6.1.4.1.37950.1.1.5.12.3.2.7.1.3
-- 1.3.6.1.4.1.37950.1.1.5.12.3.2.7.1.3
-- 1.3.6.1.4.1.37950.1.1.5.12.3.2.7.1.3
-- 1.3.6.1.4.1.37950.1.1.6.1.8.25.1.3
		-- 1.3.6.1.4.1.37950.1.1.6.1.8.25.1.3
		priNatTypeS OBJECT-TYPE
			SYNTAX INTEGER
				{
				nat1(1),
				nat2(2),
				nat3(3),
				nat4-napt(4)
				}
			MAX-ACCESS read-write
			STATUS current
			DESCRIPTION
				"Description."
			::= { priNatTypeEntry 3 }

		
--    1.3.6.1.4.1.37950.1.1.5.12.3.2.7
-- 1.3.6.1.4.1.37950.1.1.5.12.3.2.7
-- 1.3.6.1.4.1.37950.1.1.6.1.8.26
		-- 1.3.6.1.4.1.37950.1.1.6.1.8.26
		priUPnPTable OBJECT-TYPE
			SYNTAX SEQUENCE OF PriUPnPEntry
			MAX-ACCESS not-accessible
			STATUS current
			DESCRIPTION
				"Description."
			::= { gOnuPriCfgInfo 26 }

		
--     1.3.6.1.4.1.37950.1.1.5.12.3.2.7.1
-- 1.3.6.1.4.1.37950.1.1.5.12.3.2.7.1
-- 1.3.6.1.4.1.37950.1.1.5.12.3.2.7.1
-- 1.3.6.1.4.1.37950.1.1.6.1.8.26.1
		-- 1.3.6.1.4.1.37950.1.1.6.1.8.26.1
		priUPnPEntry OBJECT-TYPE
			SYNTAX PriUPnPEntry
			MAX-ACCESS not-accessible
			STATUS current
			DESCRIPTION
				"Description."
			INDEX { priUpnpPonIDS, priUpnpOnuIDS }
			::= { priUPnPTable 1 }

		
		PriUPnPEntry ::=
			SEQUENCE { 
				priUpnpPonIDS
					INTEGER,
				priUpnpOnuIDS
					INTEGER,
				priUpnpStatusS
					INTEGER,
				priUpnpWanIndexS
					Integer32,
				priUpnpSupportWanIndexS
					OCTET STRING
			 }

--     1.3.6.1.4.1.37950.1.1.5.12.3.2.7.1.1
-- 1.3.6.1.4.1.37950.1.1.5.12.3.2.7.1.1
-- 1.3.6.1.4.1.37950.1.1.5.12.3.2.7.1.1
-- 1.3.6.1.4.1.37950.1.1.6.1.8.26.1.1
		-- 1.3.6.1.4.1.37950.1.1.6.1.8.26.1.1
		priUpnpPonIDS OBJECT-TYPE
			SYNTAX INTEGER (1..16)
			MAX-ACCESS read-write
			STATUS current
			DESCRIPTION
				"Description."
			::= { priUPnPEntry 1 }

		
--     1.3.6.1.4.1.37950.1.1.5.12.3.2.7.1.2
-- 1.3.6.1.4.1.37950.1.1.5.12.3.2.7.1.2
-- 1.3.6.1.4.1.37950.1.1.5.12.3.2.7.1.2
-- 1.3.6.1.4.1.37950.1.1.6.1.8.26.1.2
		-- 1.3.6.1.4.1.37950.1.1.6.1.8.26.1.2
		priUpnpOnuIDS OBJECT-TYPE
			SYNTAX INTEGER (1..65535)
			MAX-ACCESS read-write
			STATUS current
			DESCRIPTION
				"Description."
			::= { priUPnPEntry 2 }

		
--     1.3.6.1.4.1.37950.1.1.5.12.3.2.7.1.3
-- 1.3.6.1.4.1.37950.1.1.5.12.3.2.7.1.3
-- 1.3.6.1.4.1.37950.1.1.5.12.3.2.7.1.3
-- 1.3.6.1.4.1.37950.1.1.6.1.8.26.1.3
		-- 1.3.6.1.4.1.37950.1.1.6.1.8.26.1.3
		priUpnpStatusS OBJECT-TYPE
			SYNTAX INTEGER
				{
				disable(0),
				enable(1)
				}
			MAX-ACCESS read-write
			STATUS current
			DESCRIPTION
				"Description."
			::= { priUPnPEntry 3 }

		
--  1.3.6.1.4.1.37950.1.1.6.1.8.26.1.4
		-- 1.3.6.1.4.1.37950.1.1.6.1.8.26.1.4
		priUpnpWanIndexS OBJECT-TYPE
			SYNTAX Integer32 (1..8)
			MAX-ACCESS read-write
			STATUS current
			DESCRIPTION
				"Description."
			::= { priUPnPEntry 4 }

		
--  1.3.6.1.4.1.37950.1.1.6.1.8.26.1.5
		-- 1.3.6.1.4.1.37950.1.1.6.1.8.26.1.5
		priUpnpSupportWanIndexS OBJECT-TYPE
			SYNTAX OCTET STRING
			MAX-ACCESS read-only
			STATUS current
			DESCRIPTION
				"Description."
			::= { priUPnPEntry 5 }

		
--  1.3.6.1.4.1.37950.1.1.6.1.8.27
		-- 1.3.6.1.4.1.37950.1.1.6.1.8.27
		priH248ServerTable OBJECT-TYPE
			SYNTAX SEQUENCE OF PriH248ServerEntry
			MAX-ACCESS not-accessible
			STATUS current
			DESCRIPTION
				"Description."
			::= { gOnuPriCfgInfo 27 }

		
--  1.3.6.1.4.1.37950.1.1.6.1.8.27.1
		-- 1.3.6.1.4.1.37950.1.1.6.1.8.27.1
		priH248ServerEntry OBJECT-TYPE
			SYNTAX PriH248ServerEntry
			MAX-ACCESS not-accessible
			STATUS current
			DESCRIPTION
				"Description."
			INDEX { priH248SrvPonIDS, priH248SrvOnuIDS }
			::= { priH248ServerTable 1 }

		
		PriH248ServerEntry ::=
			SEQUENCE { 
				priH248SrvPonIDS
					Integer32,
				priH248SrvOnuIDS
					Integer32,
				priH248SrvMGPortS
					Integer32,
				priH248SrvMGCServerS
					OCTET STRING,
				priH248SrvMGCPortS
					Integer32,
				priH248SrvBackupMGCServerS
					OCTET STRING,
				priH248SrvBackupMGCPortS
					Integer32,
				priH248SrvActiveMGC
					INTEGER,
				priH248SrvRegisterModeS
					INTEGER,
				priH248SrvMIDS
					OCTET STRING,
				priH248SrvHeartbeatModeS
					INTEGER,
				priH248SrvHeartbeatFormatS
					INTEGER,
				priH248SrvHeartbeatCycleS
					Integer32,
				priH248SrvHeartbeatCountS
					Integer32
			 }

--  1.3.6.1.4.1.37950.1.1.6.1.8.27.1.1
		-- 1.3.6.1.4.1.37950.1.1.6.1.8.27.1.1
		priH248SrvPonIDS OBJECT-TYPE
			SYNTAX Integer32
			MAX-ACCESS read-write
			STATUS current
			DESCRIPTION
				"Description."
			::= { priH248ServerEntry 1 }

		
--  1.3.6.1.4.1.37950.1.1.6.1.8.27.1.2
		-- 1.3.6.1.4.1.37950.1.1.6.1.8.27.1.2
		priH248SrvOnuIDS OBJECT-TYPE
			SYNTAX Integer32
			MAX-ACCESS read-write
			STATUS current
			DESCRIPTION
				"Description."
			::= { priH248ServerEntry 2 }

		
--  1.3.6.1.4.1.37950.1.1.6.1.8.27.1.3
		-- 1.3.6.1.4.1.37950.1.1.6.1.8.27.1.3
		priH248SrvMGPortS OBJECT-TYPE
			SYNTAX Integer32
			MAX-ACCESS read-write
			STATUS current
			DESCRIPTION
				"Description."
			::= { priH248ServerEntry 3 }

		
--  1.3.6.1.4.1.37950.1.1.6.1.8.27.1.4
		-- 1.3.6.1.4.1.37950.1.1.6.1.8.27.1.4
		priH248SrvMGCServerS OBJECT-TYPE
			SYNTAX OCTET STRING
			MAX-ACCESS read-write
			STATUS current
			DESCRIPTION
				"Description."
			::= { priH248ServerEntry 4 }

		
--  1.3.6.1.4.1.37950.1.1.6.1.8.27.1.5
		-- 1.3.6.1.4.1.37950.1.1.6.1.8.27.1.5
		priH248SrvMGCPortS OBJECT-TYPE
			SYNTAX Integer32
			MAX-ACCESS read-write
			STATUS current
			DESCRIPTION
				"Description."
			::= { priH248ServerEntry 5 }

		
--  1.3.6.1.4.1.37950.1.1.6.1.8.27.1.6
		-- 1.3.6.1.4.1.37950.1.1.6.1.8.27.1.6
		priH248SrvBackupMGCServerS OBJECT-TYPE
			SYNTAX OCTET STRING
			MAX-ACCESS read-write
			STATUS current
			DESCRIPTION
				"Description."
			::= { priH248ServerEntry 6 }

		
--  1.3.6.1.4.1.37950.1.1.6.1.8.27.1.7
		-- 1.3.6.1.4.1.37950.1.1.6.1.8.27.1.7
		priH248SrvBackupMGCPortS OBJECT-TYPE
			SYNTAX Integer32
			MAX-ACCESS read-write
			STATUS current
			DESCRIPTION
				"Description."
			::= { priH248ServerEntry 7 }

		
--  1.3.6.1.4.1.37950.1.1.6.1.8.27.1.8
		-- 1.3.6.1.4.1.37950.1.1.6.1.8.27.1.8
		priH248SrvActiveMGC OBJECT-TYPE
			SYNTAX INTEGER
				{
				backup_mgc(0),
				mgc(1)
				}
			MAX-ACCESS read-write
			STATUS current
			DESCRIPTION
				"Description."
			::= { priH248ServerEntry 8 }

		
--  1.3.6.1.4.1.37950.1.1.6.1.8.27.1.9
		-- 1.3.6.1.4.1.37950.1.1.6.1.8.27.1.9
		priH248SrvRegisterModeS OBJECT-TYPE
			SYNTAX INTEGER
				{
				ip_address(0),
				domain_name(1),
				device_name(2)
				}
			MAX-ACCESS read-write
			STATUS current
			DESCRIPTION
				"Description."
			::= { priH248ServerEntry 9 }

		
--  1.3.6.1.4.1.37950.1.1.6.1.8.27.1.10
		-- 1.3.6.1.4.1.37950.1.1.6.1.8.27.1.10
		priH248SrvMIDS OBJECT-TYPE
			SYNTAX OCTET STRING
			MAX-ACCESS read-write
			STATUS current
			DESCRIPTION
				"Description."
			::= { priH248ServerEntry 10 }

		
--  1.3.6.1.4.1.37950.1.1.6.1.8.27.1.11
		-- 1.3.6.1.4.1.37950.1.1.6.1.8.27.1.11
		priH248SrvHeartbeatModeS OBJECT-TYPE
			SYNTAX INTEGER
				{
				disable(0),
				active_enable(1),
				passive_enable(2)
				}
			MAX-ACCESS read-write
			STATUS current
			DESCRIPTION
				"Description."
			::= { priH248ServerEntry 11 }

		
--  1.3.6.1.4.1.37950.1.1.6.1.8.27.1.12
		-- 1.3.6.1.4.1.37950.1.1.6.1.8.27.1.12
		priH248SrvHeartbeatFormatS OBJECT-TYPE
			SYNTAX INTEGER
				{
				notify(1),
				service_change(2)
				}
			MAX-ACCESS read-write
			STATUS current
			DESCRIPTION
				"Description."
			::= { priH248ServerEntry 12 }

		
--  1.3.6.1.4.1.37950.1.1.6.1.8.27.1.13
		-- 1.3.6.1.4.1.37950.1.1.6.1.8.27.1.13
		priH248SrvHeartbeatCycleS OBJECT-TYPE
			SYNTAX Integer32
			MAX-ACCESS read-write
			STATUS current
			DESCRIPTION
				"Description."
			::= { priH248ServerEntry 13 }

		
--  1.3.6.1.4.1.37950.1.1.6.1.8.27.1.14
		-- 1.3.6.1.4.1.37950.1.1.6.1.8.27.1.14
		priH248SrvHeartbeatCountS OBJECT-TYPE
			SYNTAX Integer32
			MAX-ACCESS read-write
			STATUS current
			DESCRIPTION
				"Description."
			::= { priH248ServerEntry 14 }

		
--  1.3.6.1.4.1.37950.1.1.6.1.8.28
		-- 1.3.6.1.4.1.37950.1.1.6.1.8.28
		priH248UserTable OBJECT-TYPE
			SYNTAX SEQUENCE OF PriH248UserEntry
			MAX-ACCESS not-accessible
			STATUS current
			DESCRIPTION
				"Description."
			::= { gOnuPriCfgInfo 28 }

		
--  1.3.6.1.4.1.37950.1.1.6.1.8.28.1
		-- 1.3.6.1.4.1.37950.1.1.6.1.8.28.1
		priH248UserEntry OBJECT-TYPE
			SYNTAX PriH248UserEntry
			MAX-ACCESS not-accessible
			STATUS current
			DESCRIPTION
				"Description."
			INDEX { priH248UserPonIDS, priH248UserOnuIDS, priH248UserPortIndexS }
			::= { priH248UserTable 1 }

		
		PriH248UserEntry ::=
			SEQUENCE { 
				priH248UserPonIDS
					Integer32,
				priH248UserOnuIDS
					Integer32,
				priH248UserPortIndexS
					Integer32,
				priH248UserNameS
					OCTET STRING
			 }

--  1.3.6.1.4.1.37950.1.1.6.1.8.28.1.1
		-- 1.3.6.1.4.1.37950.1.1.6.1.8.28.1.1
		priH248UserPonIDS OBJECT-TYPE
			SYNTAX Integer32
			MAX-ACCESS read-write
			STATUS current
			DESCRIPTION
				"Description."
			::= { priH248UserEntry 1 }

		
--  1.3.6.1.4.1.37950.1.1.6.1.8.28.1.2
		-- 1.3.6.1.4.1.37950.1.1.6.1.8.28.1.2
		priH248UserOnuIDS OBJECT-TYPE
			SYNTAX Integer32
			MAX-ACCESS read-write
			STATUS current
			DESCRIPTION
				"Description."
			::= { priH248UserEntry 2 }

		
--  1.3.6.1.4.1.37950.1.1.6.1.8.28.1.3
		-- 1.3.6.1.4.1.37950.1.1.6.1.8.28.1.3
		priH248UserPortIndexS OBJECT-TYPE
			SYNTAX Integer32
			MAX-ACCESS read-write
			STATUS current
			DESCRIPTION
				"Description."
			::= { priH248UserEntry 3 }

		
--  1.3.6.1.4.1.37950.1.1.6.1.8.28.1.4
		-- 1.3.6.1.4.1.37950.1.1.6.1.8.28.1.4
		priH248UserNameS OBJECT-TYPE
			SYNTAX OCTET STRING
			MAX-ACCESS read-write
			STATUS current
			DESCRIPTION
				"Description."
			::= { priH248UserEntry 4 }

		
--  1.3.6.1.4.1.37950.1.1.6.1.8.29
		-- 1.3.6.1.4.1.37950.1.1.6.1.8.29
		priH248SignalMediaAloneTable OBJECT-TYPE
			SYNTAX SEQUENCE OF PriH248SignalMediaAloneEntry
			MAX-ACCESS not-accessible
			STATUS current
			DESCRIPTION
				"Description."
			::= { gOnuPriCfgInfo 29 }

		
--  1.3.6.1.4.1.37950.1.1.6.1.8.29.1
		-- 1.3.6.1.4.1.37950.1.1.6.1.8.29.1
		priH248SignalMediaAloneEntry OBJECT-TYPE
			SYNTAX PriH248SignalMediaAloneEntry
			MAX-ACCESS not-accessible
			STATUS current
			DESCRIPTION
				"Description."
			INDEX { priH248SMAPonIDS, priH248SMAOnuIDS }
			::= { priH248SignalMediaAloneTable 1 }

		
		PriH248SignalMediaAloneEntry ::=
			SEQUENCE { 
				priH248SMAPonIDS
					Integer32,
				priH248SMAOnuIDS
					Integer32,
				priH248SMAStatusS
					INTEGER,
				priH248SMAWanIndexS
					Integer32,
				priH248SMASupportWanIndexS
					OCTET STRING
			 }

--  1.3.6.1.4.1.37950.1.1.6.1.8.29.1.1
		-- 1.3.6.1.4.1.37950.1.1.6.1.8.29.1.1
		priH248SMAPonIDS OBJECT-TYPE
			SYNTAX Integer32
			MAX-ACCESS read-write
			STATUS current
			DESCRIPTION
				"Description."
			::= { priH248SignalMediaAloneEntry 1 }

		
--  1.3.6.1.4.1.37950.1.1.6.1.8.29.1.2
		-- 1.3.6.1.4.1.37950.1.1.6.1.8.29.1.2
		priH248SMAOnuIDS OBJECT-TYPE
			SYNTAX Integer32
			MAX-ACCESS read-write
			STATUS current
			DESCRIPTION
				"Description."
			::= { priH248SignalMediaAloneEntry 2 }

		
--  1.3.6.1.4.1.37950.1.1.6.1.8.29.1.3
		-- 1.3.6.1.4.1.37950.1.1.6.1.8.29.1.3
		priH248SMAStatusS OBJECT-TYPE
			SYNTAX INTEGER
				{
				disable(0),
				enable(1)
				}
			MAX-ACCESS read-write
			STATUS current
			DESCRIPTION
				"Description."
			::= { priH248SignalMediaAloneEntry 3 }

		
--  1.3.6.1.4.1.37950.1.1.6.1.8.29.1.4
		-- 1.3.6.1.4.1.37950.1.1.6.1.8.29.1.4
		priH248SMAWanIndexS OBJECT-TYPE
			SYNTAX Integer32
			MAX-ACCESS read-write
			STATUS current
			DESCRIPTION
				"Description."
			::= { priH248SignalMediaAloneEntry 4 }

		
--  1.3.6.1.4.1.37950.1.1.6.1.8.29.1.5
		-- 1.3.6.1.4.1.37950.1.1.6.1.8.29.1.5
		priH248SMASupportWanIndexS OBJECT-TYPE
			SYNTAX OCTET STRING
			MAX-ACCESS read-write
			STATUS current
			DESCRIPTION
				"Description."
			::= { priH248SignalMediaAloneEntry 5 }

		
--  1.3.6.1.4.1.37950.1.1.6.1.8.30
		-- 1.3.6.1.4.1.37950.1.1.6.1.8.30
		priMacAclRuleTable OBJECT-TYPE
			SYNTAX SEQUENCE OF PriMacAclRuleEntry
			MAX-ACCESS not-accessible
			STATUS current
			DESCRIPTION
				"Description."
			::= { gOnuPriCfgInfo 30 }

		
--  1.3.6.1.4.1.37950.1.1.6.1.8.30.1
		-- 1.3.6.1.4.1.37950.1.1.6.1.8.30.1
		priMacAclRuleEntry OBJECT-TYPE
			SYNTAX PriMacAclRuleEntry
			MAX-ACCESS not-accessible
			STATUS current
			DESCRIPTION
				"Description."
			INDEX { priMRulePonIDS, priMRuleOnuIDS }
			::= { priMacAclRuleTable 1 }

		
		PriMacAclRuleEntry ::=
			SEQUENCE { 
				priMRulePonIDS
					Integer32,
				priMRuleOnuIDS
					Integer32,
				priMRuleStatusS
					INTEGER,
				priMRuleModeS
					INTEGER
			 }

--  1.3.6.1.4.1.37950.1.1.6.1.8.30.1.1
		-- 1.3.6.1.4.1.37950.1.1.6.1.8.30.1.1
		priMRulePonIDS OBJECT-TYPE
			SYNTAX Integer32
			MAX-ACCESS read-write
			STATUS current
			DESCRIPTION
				"Description."
			::= { priMacAclRuleEntry 1 }

		
--  1.3.6.1.4.1.37950.1.1.6.1.8.30.1.2
		-- 1.3.6.1.4.1.37950.1.1.6.1.8.30.1.2
		priMRuleOnuIDS OBJECT-TYPE
			SYNTAX Integer32
			MAX-ACCESS read-write
			STATUS current
			DESCRIPTION
				"Description."
			::= { priMacAclRuleEntry 2 }

		
--  1.3.6.1.4.1.37950.1.1.6.1.8.30.1.3
		-- 1.3.6.1.4.1.37950.1.1.6.1.8.30.1.3
		priMRuleStatusS OBJECT-TYPE
			SYNTAX INTEGER
				{
				disable(0),
				enable(1)
				}
			MAX-ACCESS read-write
			STATUS current
			DESCRIPTION
				"Description."
			::= { priMacAclRuleEntry 3 }

		
--  1.3.6.1.4.1.37950.1.1.6.1.8.30.1.4
		-- 1.3.6.1.4.1.37950.1.1.6.1.8.30.1.4
		priMRuleModeS OBJECT-TYPE
			SYNTAX INTEGER { whitelist(0) }
			MAX-ACCESS read-write
			STATUS current
			DESCRIPTION
				"Description."
			::= { priMacAclRuleEntry 4 }

		
--  1.3.6.1.4.1.37950.1.1.6.1.8.31
		-- 1.3.6.1.4.1.37950.1.1.6.1.8.31
		priMacAclGroupTable OBJECT-TYPE
			SYNTAX SEQUENCE OF PriMacAclGroupEntry
			MAX-ACCESS not-accessible
			STATUS current
			DESCRIPTION
				"Description."
			::= { gOnuPriCfgInfo 31 }

		
--  1.3.6.1.4.1.37950.1.1.6.1.8.31.1
		-- 1.3.6.1.4.1.37950.1.1.6.1.8.31.1
		priMacAclGroupEntry OBJECT-TYPE
			SYNTAX PriMacAclGroupEntry
			MAX-ACCESS not-accessible
			STATUS current
			DESCRIPTION
				"Description."
			INDEX { priMGroupPonIDS, priMGroupOnuIDS, priMGroupGroupNumS }
			::= { priMacAclGroupTable 1 }

		
		PriMacAclGroupEntry ::=
			SEQUENCE { 
				priMGroupPonIDS
					Integer32,
				priMGroupOnuIDS
					Integer32,
				priMGroupGroupNumS
					Integer32,
				priMGroupMACS
					OCTET STRING,
				priMGroupMaskS
					OCTET STRING
			 }

--  1.3.6.1.4.1.37950.1.1.6.1.8.31.1.1
		-- 1.3.6.1.4.1.37950.1.1.6.1.8.31.1.1
		priMGroupPonIDS OBJECT-TYPE
			SYNTAX Integer32
			MAX-ACCESS read-write
			STATUS current
			DESCRIPTION
				"Description."
			::= { priMacAclGroupEntry 1 }

		
--  1.3.6.1.4.1.37950.1.1.6.1.8.31.1.2
		-- 1.3.6.1.4.1.37950.1.1.6.1.8.31.1.2
		priMGroupOnuIDS OBJECT-TYPE
			SYNTAX Integer32
			MAX-ACCESS read-write
			STATUS current
			DESCRIPTION
				"Description."
			::= { priMacAclGroupEntry 2 }

		
--  1.3.6.1.4.1.37950.1.1.6.1.8.31.1.3
		-- 1.3.6.1.4.1.37950.1.1.6.1.8.31.1.3
		priMGroupGroupNumS OBJECT-TYPE
			SYNTAX Integer32
			MAX-ACCESS read-write
			STATUS current
			DESCRIPTION
				"Description."
			::= { priMacAclGroupEntry 3 }

		
--  1.3.6.1.4.1.37950.1.1.6.1.8.31.1.4
		-- 1.3.6.1.4.1.37950.1.1.6.1.8.31.1.4
		priMGroupMACS OBJECT-TYPE
			SYNTAX OCTET STRING
			MAX-ACCESS read-write
			STATUS current
			DESCRIPTION
				"Description."
			::= { priMacAclGroupEntry 4 }

		
--  1.3.6.1.4.1.37950.1.1.6.1.8.31.1.5
		-- 1.3.6.1.4.1.37950.1.1.6.1.8.31.1.5
		priMGroupMaskS OBJECT-TYPE
			SYNTAX OCTET STRING
			MAX-ACCESS read-write
			STATUS current
			DESCRIPTION
				"Description."
			::= { priMacAclGroupEntry 5 }

		
--  1.3.6.1.4.1.37950.1.1.6.1.8.32
		-- 1.3.6.1.4.1.37950.1.1.6.1.8.32
		priModeTable OBJECT-TYPE
			SYNTAX SEQUENCE OF PriModeEntry
			MAX-ACCESS not-accessible
			STATUS current
			DESCRIPTION
				"Description."
			::= { gOnuPriCfgInfo 32 }

		
--  1.3.6.1.4.1.37950.1.1.6.1.8.32.1
		-- 1.3.6.1.4.1.37950.1.1.6.1.8.32.1
		priModeEntry OBJECT-TYPE
			SYNTAX PriModeEntry
			MAX-ACCESS not-accessible
			STATUS current
			DESCRIPTION
				"Description."
			INDEX { priModePonIDS, priModeOnuIDS }
			::= { priModeTable 1 }

		
		PriModeEntry ::=
			SEQUENCE { 
				priModePonIDS
					Integer32,
				priModeOnuIDS
					Integer32,
				priModeSelectStatusS
					INTEGER,
				priModeSelectS
					INTEGER
			 }

--  1.3.6.1.4.1.37950.1.1.6.1.8.32.1.1
		-- 1.3.6.1.4.1.37950.1.1.6.1.8.32.1.1
		priModePonIDS OBJECT-TYPE
			SYNTAX Integer32
			MAX-ACCESS read-write
			STATUS current
			DESCRIPTION
				"Description."
			::= { priModeEntry 1 }

		
--  1.3.6.1.4.1.37950.1.1.6.1.8.32.1.2
		-- 1.3.6.1.4.1.37950.1.1.6.1.8.32.1.2
		priModeOnuIDS OBJECT-TYPE
			SYNTAX Integer32
			MAX-ACCESS read-write
			STATUS current
			DESCRIPTION
				"Description."
			::= { priModeEntry 2 }

		
--  1.3.6.1.4.1.37950.1.1.6.1.8.32.1.3
		-- 1.3.6.1.4.1.37950.1.1.6.1.8.32.1.3
		priModeSelectStatusS OBJECT-TYPE
			SYNTAX INTEGER
				{
				disable(0),
				enable(1)
				}
			MAX-ACCESS read-write
			STATUS current
			DESCRIPTION
				"Description."
			::= { priModeEntry 3 }

		
--  1.3.6.1.4.1.37950.1.1.6.1.8.32.1.4
		-- 1.3.6.1.4.1.37950.1.1.6.1.8.32.1.4
		priModeSelectS OBJECT-TYPE
			SYNTAX INTEGER
				{
				sfu(0),
				hgu(1),
				auto(2)
				}
			MAX-ACCESS read-write
			STATUS current
			DESCRIPTION
				"Description."
			::= { priModeEntry 4 }

		
--  1.3.6.1.4.1.37950.1.1.6.1.8.33
		-- 1.3.6.1.4.1.37950.1.1.6.1.8.33
		priMQTTTable OBJECT-TYPE
			SYNTAX SEQUENCE OF PriMQTTEntry
			MAX-ACCESS not-accessible
			STATUS current
			DESCRIPTION
				"Description."
			::= { gOnuPriCfgInfo 33 }

		
--  1.3.6.1.4.1.37950.1.1.6.1.8.33.1
		-- 1.3.6.1.4.1.37950.1.1.6.1.8.33.1
		priMQTTEntry OBJECT-TYPE
			SYNTAX PriMQTTEntry
			MAX-ACCESS not-accessible
			STATUS current
			DESCRIPTION
				"Description."
			INDEX { priMQTTPonIDS, priMQTTOnuIDS }
			::= { priMQTTTable 1 }

		
		PriMQTTEntry ::=
			SEQUENCE { 
				priMQTTPonIDS
					Integer32,
				priMQTTOnuIDS
					Integer32,
				priMQTTConnectStatusS
					INTEGER,
				priMQTTEnableStatusS
					INTEGER,
				priMQTTAddressS
					OCTET STRING,
				priMQTTUserNameS
					OCTET STRING,
				priMQTTPasswordS
					OCTET STRING,
				priMQTTIDS
					OCTET STRING
			 }

--  1.3.6.1.4.1.37950.1.1.6.1.8.33.1.1
		-- 1.3.6.1.4.1.37950.1.1.6.1.8.33.1.1
		priMQTTPonIDS OBJECT-TYPE
			SYNTAX Integer32
			MAX-ACCESS read-write
			STATUS current
			DESCRIPTION
				"Description."
			::= { priMQTTEntry 1 }

		
--  1.3.6.1.4.1.37950.1.1.6.1.8.33.1.2
		-- 1.3.6.1.4.1.37950.1.1.6.1.8.33.1.2
		priMQTTOnuIDS OBJECT-TYPE
			SYNTAX Integer32
			MAX-ACCESS read-write
			STATUS current
			DESCRIPTION
				"Description."
			::= { priMQTTEntry 2 }

		
--  1.3.6.1.4.1.37950.1.1.6.1.8.33.1.3
		-- 1.3.6.1.4.1.37950.1.1.6.1.8.33.1.3
		priMQTTConnectStatusS OBJECT-TYPE
			SYNTAX INTEGER
				{
				disconnected(0),
				connected(1)
				}
			MAX-ACCESS read-write
			STATUS current
			DESCRIPTION
				"Description."
			::= { priMQTTEntry 3 }

		
--  1.3.6.1.4.1.37950.1.1.6.1.8.33.1.4
		-- 1.3.6.1.4.1.37950.1.1.6.1.8.33.1.4
		priMQTTEnableStatusS OBJECT-TYPE
			SYNTAX INTEGER
				{
				disable(0),
				enable(1)
				}
			MAX-ACCESS read-write
			STATUS current
			DESCRIPTION
				"Description."
			::= { priMQTTEntry 4 }

		
--  1.3.6.1.4.1.37950.1.1.6.1.8.33.1.5
		-- 1.3.6.1.4.1.37950.1.1.6.1.8.33.1.5
		priMQTTAddressS OBJECT-TYPE
			SYNTAX OCTET STRING
			MAX-ACCESS read-write
			STATUS current
			DESCRIPTION
				"Description."
			::= { priMQTTEntry 5 }

		
--  1.3.6.1.4.1.37950.1.1.6.1.8.33.1.6
		-- 1.3.6.1.4.1.37950.1.1.6.1.8.33.1.6
		priMQTTUserNameS OBJECT-TYPE
			SYNTAX OCTET STRING
			MAX-ACCESS read-write
			STATUS current
			DESCRIPTION
				"Description."
			::= { priMQTTEntry 6 }

		
--  1.3.6.1.4.1.37950.1.1.6.1.8.33.1.7
		-- 1.3.6.1.4.1.37950.1.1.6.1.8.33.1.7
		priMQTTPasswordS OBJECT-TYPE
			SYNTAX OCTET STRING
			MAX-ACCESS read-write
			STATUS current
			DESCRIPTION
				"Description."
			::= { priMQTTEntry 7 }

		
--  1.3.6.1.4.1.37950.1.1.6.1.8.33.1.8
		-- 1.3.6.1.4.1.37950.1.1.6.1.8.33.1.8
		priMQTTIDS OBJECT-TYPE
			SYNTAX OCTET STRING
			MAX-ACCESS read-write
			STATUS current
			DESCRIPTION
				"Description."
			::= { priMQTTEntry 8 }

		
		-- 1.3.6.1.4.1.37950.1.1.6.1.8.34
		priAPTable OBJECT-TYPE
			SYNTAX SEQUENCE OF PriAPEntry
			MAX-ACCESS not-accessible
			STATUS current
			DESCRIPTION
				"Description."
			::= { gOnuPriCfgInfo 34 }

		
		-- 1.3.6.1.4.1.37950.1.1.6.1.8.34.1
		priAPEntry OBJECT-TYPE
			SYNTAX PriAPEntry
			MAX-ACCESS not-accessible
			STATUS current
			DESCRIPTION
				"Description."
			INDEX { priAPPonIDS, priAPOnuIDS }
			::= { priAPTable 1 }

		
		PriAPEntry ::=
			SEQUENCE { 
				priAPPonIDS
					Integer32,
				priAPOnuIDS
					Integer32,
				priAPStatusS
					INTEGER,
				priAPVLANS
					Integer32
			 }

		-- 1.3.6.1.4.1.37950.1.1.6.1.8.34.1.1
		priAPPonIDS OBJECT-TYPE
			SYNTAX Integer32
			MAX-ACCESS read-write
			STATUS current
			DESCRIPTION
				"Description."
			::= { priAPEntry 1 }

		
		-- 1.3.6.1.4.1.37950.1.1.6.1.8.34.1.2
		priAPOnuIDS OBJECT-TYPE
			SYNTAX Integer32
			MAX-ACCESS read-write
			STATUS current
			DESCRIPTION
				"Description."
			::= { priAPEntry 2 }

		
		-- 1.3.6.1.4.1.37950.1.1.6.1.8.34.1.3
		priAPStatusS OBJECT-TYPE
			SYNTAX INTEGER
				{
				disable(0),
				enable(1)
				}
			MAX-ACCESS read-write
			STATUS current
			DESCRIPTION
				"Description."
			::= { priAPEntry 3 }

		
		-- 1.3.6.1.4.1.37950.1.1.6.1.8.34.1.4
		priAPVLANS OBJECT-TYPE
			SYNTAX Integer32
			MAX-ACCESS read-write
			STATUS current
			DESCRIPTION
				"Description."
			::= { priAPEntry 4 }

		
--  1.3.6.1.4.1.37950.1.1.6.2
		-- 1.3.6.1.4.1.37950.1.1.6.2
		v1600gProfile OBJECT IDENTIFIER ::= { v1600g 2 }

		
--  1.3.6.1.4.1.37950.1.1.6.2.1
		-- 1.3.6.1.4.1.37950.1.1.6.2.1
		v1600gProfileCfg OBJECT IDENTIFIER ::= { v1600gProfile 1 }

		
--  1.3.6.1.4.1.37950.1.1.6.2.1.1
		-- 1.3.6.1.4.1.37950.1.1.6.2.1.1
		v1600gOnuProfileCfg OBJECT IDENTIFIER ::= { v1600gProfileCfg 1 }

		
--  1.3.6.1.4.1.37950.1.1.6.2.1.1.1
		-- 1.3.6.1.4.1.37950.1.1.6.2.1.1.1
		onuPName OBJECT-TYPE
			SYNTAX OCTET STRING (SIZE (1..64))
			MAX-ACCESS read-write
			STATUS current
			DESCRIPTION
				"Description."
			::= { v1600gOnuProfileCfg 1 }

		
--  1.3.6.1.4.1.37950.1.1.6.2.1.1.2
		-- 1.3.6.1.4.1.37950.1.1.6.2.1.1.2
		onuPDesc OBJECT-TYPE
			SYNTAX OCTET STRING
			MAX-ACCESS read-write
			STATUS current
			DESCRIPTION
				"Description."
			::= { v1600gOnuProfileCfg 2 }

		
--  1.3.6.1.4.1.37950.1.1.6.2.1.1.3
		-- 1.3.6.1.4.1.37950.1.1.6.2.1.1.3
		onuPMaxTcont OBJECT-TYPE
			SYNTAX Integer32 (1..255)
			MAX-ACCESS read-write
			STATUS current
			DESCRIPTION
				"Description."
			::= { v1600gOnuProfileCfg 3 }

		
--  1.3.6.1.4.1.37950.1.1.6.2.1.1.4
		-- 1.3.6.1.4.1.37950.1.1.6.2.1.1.4
		onuPMaxGemport OBJECT-TYPE
			SYNTAX Integer32 (1..255)
			MAX-ACCESS read-write
			STATUS current
			DESCRIPTION
				"Description."
			::= { v1600gOnuProfileCfg 4 }

		
--  1.3.6.1.4.1.37950.1.1.6.2.1.1.5
		-- 1.3.6.1.4.1.37950.1.1.6.2.1.1.5
		onuPMaxEth OBJECT-TYPE
			SYNTAX Integer32 (0..255)
			MAX-ACCESS read-write
			STATUS current
			DESCRIPTION
				"Description."
			::= { v1600gOnuProfileCfg 5 }

		
--  1.3.6.1.4.1.37950.1.1.6.2.1.1.6
		-- 1.3.6.1.4.1.37950.1.1.6.2.1.1.6
		onuPMaxPots OBJECT-TYPE
			SYNTAX Integer32 (0..255)
			MAX-ACCESS read-write
			STATUS current
			DESCRIPTION
				"Description."
			::= { v1600gOnuProfileCfg 6 }

		
--  1.3.6.1.4.1.37950.1.1.6.2.1.1.7
		-- 1.3.6.1.4.1.37950.1.1.6.2.1.1.7
		onuPMaxIphost OBJECT-TYPE
			SYNTAX Integer32 (0..255)
			MAX-ACCESS read-write
			STATUS current
			DESCRIPTION
				"Description."
			::= { v1600gOnuProfileCfg 7 }

		
--  1.3.6.1.4.1.37950.1.1.6.2.1.1.8
		-- 1.3.6.1.4.1.37950.1.1.6.2.1.1.8
		onuPMaxIpv6host OBJECT-TYPE
			SYNTAX Integer32 (0..255)
			MAX-ACCESS read-write
			STATUS current
			DESCRIPTION
				"Description."
			::= { v1600gOnuProfileCfg 8 }

		
--  1.3.6.1.4.1.37950.1.1.6.2.1.1.9
		-- 1.3.6.1.4.1.37950.1.1.6.2.1.1.9
		onuPMaxVeip OBJECT-TYPE
			SYNTAX Integer32 (0..127)
			MAX-ACCESS read-write
			STATUS current
			DESCRIPTION
				"Description."
			::= { v1600gOnuProfileCfg 9 }

		
--  1.3.6.1.4.1.37950.1.1.6.2.1.1.10
		-- 1.3.6.1.4.1.37950.1.1.6.2.1.1.10
		onuPSrvAbility OBJECT-TYPE
			SYNTAX INTEGER
				{
				disable(0),
				enable(1)
				}
			MAX-ACCESS read-write
			STATUS current
			DESCRIPTION
				"Description."
			::= { v1600gOnuProfileCfg 10 }

		
--  1.3.6.1.4.1.37950.1.1.6.2.1.1.11
		-- 1.3.6.1.4.1.37950.1.1.6.2.1.1.11
		onuPSrvAbilityN1 OBJECT-TYPE
			SYNTAX INTEGER
				{
				no(0),
				yes(1)
				}
			MAX-ACCESS read-write
			STATUS current
			DESCRIPTION
				"Description."
			::= { v1600gOnuProfileCfg 11 }

		
--  1.3.6.1.4.1.37950.1.1.6.2.1.1.12
		-- 1.3.6.1.4.1.37950.1.1.6.2.1.1.12
		onuPSrvAbility1M OBJECT-TYPE
			SYNTAX INTEGER
				{
				no(0),
				yes(1)
				}
			MAX-ACCESS read-write
			STATUS current
			DESCRIPTION
				"Description."
			::= { v1600gOnuProfileCfg 12 }

		
--  1.3.6.1.4.1.37950.1.1.6.2.1.1.13
		-- 1.3.6.1.4.1.37950.1.1.6.2.1.1.13
		onuPSrvAbility1P OBJECT-TYPE
			SYNTAX INTEGER
				{
				no(0),
				yes(1)
				}
			MAX-ACCESS read-write
			STATUS current
			DESCRIPTION
				"Description."
			::= { v1600gOnuProfileCfg 13 }

		
--  1.3.6.1.4.1.37950.1.1.6.2.1.1.14
		-- 1.3.6.1.4.1.37950.1.1.6.2.1.1.14
		onuPWMVNOmci OBJECT-TYPE
			SYNTAX INTEGER
				{
				disable(0),
				enable(1)
				}
			MAX-ACCESS read-write
			STATUS current
			DESCRIPTION
				"Description."
			::= { v1600gOnuProfileCfg 14 }

		
--  1.3.6.1.4.1.37950.1.1.6.2.1.1.15
		-- 1.3.6.1.4.1.37950.1.1.6.2.1.1.15
		onuPOmciSMode OBJECT-TYPE
			SYNTAX INTEGER
				{
				async(0),
				sync(1)
				}
			MAX-ACCESS read-write
			STATUS current
			DESCRIPTION
				"Description."
			::= { v1600gOnuProfileCfg 15 }

		
--  1.3.6.1.4.1.37950.1.1.6.2.1.1.16
		-- 1.3.6.1.4.1.37950.1.1.6.2.1.1.16
		onuPDMrange OBJECT-TYPE
			SYNTAX INTEGER
				{
				none(0),
				all-inclusive(1)
				}
			MAX-ACCESS read-write
			STATUS current
			DESCRIPTION
				"Description."
			::= { v1600gOnuProfileCfg 16 }

		
--  1.3.6.1.4.1.37950.1.1.6.2.1.1.17
		-- 1.3.6.1.4.1.37950.1.1.6.2.1.1.17
		onuPAction OBJECT-TYPE
			SYNTAX INTEGER
				{
				add(1),
				del(2),
				commit(3)
				}
			MAX-ACCESS read-write
			STATUS current
			DESCRIPTION
				"Description."
			::= { v1600gOnuProfileCfg 17 }

		
--  1.3.6.1.4.1.37950.1.1.6.2.1.2
		-- 1.3.6.1.4.1.37950.1.1.6.2.1.2
		v1600gDbaProfileCfg OBJECT IDENTIFIER ::= { v1600gProfileCfg 2 }

		
--  1.3.6.1.4.1.37950.1.1.6.2.1.2.1
		-- 1.3.6.1.4.1.37950.1.1.6.2.1.2.1
		dbaPName OBJECT-TYPE
			SYNTAX OCTET STRING
			MAX-ACCESS read-write
			STATUS current
			DESCRIPTION
				"Description."
			::= { v1600gDbaProfileCfg 1 }

		
--  1.3.6.1.4.1.37950.1.1.6.2.1.2.2
		-- 1.3.6.1.4.1.37950.1.1.6.2.1.2.2
		dbaPType OBJECT-TYPE
			SYNTAX Integer32 (1..5)
			MAX-ACCESS read-write
			STATUS current
			DESCRIPTION
				"Description."
			::= { v1600gDbaProfileCfg 2 }

		
--  1.3.6.1.4.1.37950.1.1.6.2.1.2.3
		-- 1.3.6.1.4.1.37950.1.1.6.2.1.2.3
		dbaPFixed OBJECT-TYPE
			SYNTAX Integer32 (64..2488320)
			MAX-ACCESS read-write
			STATUS current
			DESCRIPTION
				"Description."
			::= { v1600gDbaProfileCfg 3 }

		
--  1.3.6.1.4.1.37950.1.1.6.2.1.2.4
		-- 1.3.6.1.4.1.37950.1.1.6.2.1.2.4
		dbaPAssured OBJECT-TYPE
			SYNTAX Integer32 (64..2488320)
			MAX-ACCESS read-write
			STATUS current
			DESCRIPTION
				"Description."
			::= { v1600gDbaProfileCfg 4 }

		
--  1.3.6.1.4.1.37950.1.1.6.2.1.2.5
		-- 1.3.6.1.4.1.37950.1.1.6.2.1.2.5
		dbaPMaximum OBJECT-TYPE
			SYNTAX Integer32 (64..2488320)
			MAX-ACCESS read-write
			STATUS current
			DESCRIPTION
				"Description."
			::= { v1600gDbaProfileCfg 5 }

		
--  1.3.6.1.4.1.37950.1.1.6.2.1.2.6
		-- 1.3.6.1.4.1.37950.1.1.6.2.1.2.6
		dbaPPriority OBJECT-TYPE
			SYNTAX Integer32 (1..4)
			MAX-ACCESS read-write
			STATUS current
			DESCRIPTION
				"Description."
			::= { v1600gDbaProfileCfg 6 }

		
--  1.3.6.1.4.1.37950.1.1.6.2.1.2.7
		-- 1.3.6.1.4.1.37950.1.1.6.2.1.2.7
		dbaPWeight OBJECT-TYPE
			SYNTAX Integer32 (1..1000)
			MAX-ACCESS read-write
			STATUS current
			DESCRIPTION
				"Description."
			::= { v1600gDbaProfileCfg 7 }

		
--  1.3.6.1.4.1.37950.1.1.6.2.1.2.8
		-- 1.3.6.1.4.1.37950.1.1.6.2.1.2.8
		dbaPAction OBJECT-TYPE
			SYNTAX INTEGER
				{
				add(1),
				del(2),
				commit(3)
				}
			MAX-ACCESS read-write
			STATUS current
			DESCRIPTION
				"Description."
			::= { v1600gDbaProfileCfg 8 }

		
--  1.3.6.1.4.1.37950.1.1.6.2.1.3
		-- 1.3.6.1.4.1.37950.1.1.6.2.1.3
		v1600gTrafficProfileCfg OBJECT IDENTIFIER ::= { v1600gProfileCfg 3 }

		
--  1.3.6.1.4.1.37950.1.1.6.2.1.3.1
		-- 1.3.6.1.4.1.37950.1.1.6.2.1.3.1
		trafficPName OBJECT-TYPE
			SYNTAX OCTET STRING
			MAX-ACCESS read-write
			STATUS current
			DESCRIPTION
				"Description."
			::= { v1600gTrafficProfileCfg 1 }

		
--  1.3.6.1.4.1.37950.1.1.6.2.1.3.2
		-- 1.3.6.1.4.1.37950.1.1.6.2.1.3.2
		trafficPSir OBJECT-TYPE
			SYNTAX Integer32 (0..10000000)
			MAX-ACCESS read-write
			STATUS current
			DESCRIPTION
				"Description."
			::= { v1600gTrafficProfileCfg 2 }

		
--  1.3.6.1.4.1.37950.1.1.6.2.1.3.3
		-- 1.3.6.1.4.1.37950.1.1.6.2.1.3.3
		trafficPPir OBJECT-TYPE
			SYNTAX Integer32 (64..10000000)
			MAX-ACCESS read-write
			STATUS current
			DESCRIPTION
				"Description."
			::= { v1600gTrafficProfileCfg 3 }

		
--  1.3.6.1.4.1.37950.1.1.6.2.1.3.4
		-- 1.3.6.1.4.1.37950.1.1.6.2.1.3.4
		trafficPCbs OBJECT-TYPE
			SYNTAX Integer32 (0..1024)
			MAX-ACCESS read-write
			STATUS current
			DESCRIPTION
				"Description."
			::= { v1600gTrafficProfileCfg 4 }

		
--  1.3.6.1.4.1.37950.1.1.6.2.1.3.5
		-- 1.3.6.1.4.1.37950.1.1.6.2.1.3.5
		trafficPPbs OBJECT-TYPE
			SYNTAX Integer32 (0..1024)
			MAX-ACCESS read-write
			STATUS current
			DESCRIPTION
				"Description."
			::= { v1600gTrafficProfileCfg 5 }

		
--  1.3.6.1.4.1.37950.1.1.6.2.1.3.6
		-- 1.3.6.1.4.1.37950.1.1.6.2.1.3.6
		trafficPAction OBJECT-TYPE
			SYNTAX INTEGER
				{
				add(1),
				del(2),
				commit(3)
				}
			MAX-ACCESS read-write
			STATUS current
			DESCRIPTION
				"Description."
			::= { v1600gTrafficProfileCfg 6 }

		
--  1.3.6.1.4.1.37950.1.1.6.2.1.4
		-- 1.3.6.1.4.1.37950.1.1.6.2.1.4
		v1600gLineProfileCfg OBJECT IDENTIFIER ::= { v1600gProfileCfg 4 }

		
--  1.3.6.1.4.1.37950.1.1.6.2.1.4.1
		-- 1.3.6.1.4.1.37950.1.1.6.2.1.4.1
		linePName OBJECT-TYPE
			SYNTAX OCTET STRING
			MAX-ACCESS read-write
			STATUS current
			DESCRIPTION
				"Description."
			::= { v1600gLineProfileCfg 1 }

		
--  1.3.6.1.4.1.37950.1.1.6.2.1.4.2
		-- 1.3.6.1.4.1.37950.1.1.6.2.1.4.2
		linePNameAction OBJECT-TYPE
			SYNTAX INTEGER
				{
				add(1),
				del(2),
				commit(3)
				}
			MAX-ACCESS read-write
			STATUS current
			DESCRIPTION
				"Description."
			::= { v1600gLineProfileCfg 2 }

		
--  1.3.6.1.4.1.37950.1.1.6.2.1.4.3
		-- 1.3.6.1.4.1.37950.1.1.6.2.1.4.3
		linePTcont OBJECT IDENTIFIER ::= { v1600gLineProfileCfg 3 }

		
--  1.3.6.1.4.1.37950.1.1.6.2.1.4.3.1
		-- 1.3.6.1.4.1.37950.1.1.6.2.1.4.3.1
		linePTcontId OBJECT-TYPE
			SYNTAX Integer32 (1..255)
			MAX-ACCESS read-write
			STATUS current
			DESCRIPTION
				"Description."
			::= { linePTcont 1 }

		
--  1.3.6.1.4.1.37950.1.1.6.2.1.4.3.2
		-- 1.3.6.1.4.1.37950.1.1.6.2.1.4.3.2
		linePTcontName OBJECT-TYPE
			SYNTAX OCTET STRING
			MAX-ACCESS read-write
			STATUS current
			DESCRIPTION
				"Description."
			::= { linePTcont 2 }

		
--  1.3.6.1.4.1.37950.1.1.6.2.1.4.3.3
		-- 1.3.6.1.4.1.37950.1.1.6.2.1.4.3.3
		linePTcontDbaName OBJECT-TYPE
			SYNTAX OCTET STRING
			MAX-ACCESS read-write
			STATUS current
			DESCRIPTION
				"Description."
			::= { linePTcont 3 }

		
--  1.3.6.1.4.1.37950.1.1.6.2.1.4.3.4
		-- 1.3.6.1.4.1.37950.1.1.6.2.1.4.3.4
		linePTcontAction OBJECT-TYPE
			SYNTAX INTEGER
				{
				add(1),
				del(2)
				}
			MAX-ACCESS read-write
			STATUS current
			DESCRIPTION
				"Description."
			::= { linePTcont 4 }

		
--  1.3.6.1.4.1.37950.1.1.6.2.1.4.4
		-- 1.3.6.1.4.1.37950.1.1.6.2.1.4.4
		linePGemport OBJECT IDENTIFIER ::= { v1600gLineProfileCfg 4 }

		
--  1.3.6.1.4.1.37950.1.1.6.2.1.4.4.1
		-- 1.3.6.1.4.1.37950.1.1.6.2.1.4.4.1
		linePGemId OBJECT-TYPE
			SYNTAX Integer32 (1..255)
			MAX-ACCESS read-write
			STATUS current
			DESCRIPTION
				"Description."
			::= { linePGemport 1 }

		
--  1.3.6.1.4.1.37950.1.1.6.2.1.4.4.2
		-- 1.3.6.1.4.1.37950.1.1.6.2.1.4.4.2
		linePGemTcontId OBJECT-TYPE
			SYNTAX Integer32 (1..255)
			MAX-ACCESS read-write
			STATUS current
			DESCRIPTION
				"Description."
			::= { linePGemport 2 }

		
--  1.3.6.1.4.1.37950.1.1.6.2.1.4.4.3
		-- 1.3.6.1.4.1.37950.1.1.6.2.1.4.4.3
		linePGemName OBJECT-TYPE
			SYNTAX OCTET STRING
			MAX-ACCESS read-write
			STATUS current
			DESCRIPTION
				"Description."
			::= { linePGemport 3 }

		
--  1.3.6.1.4.1.37950.1.1.6.2.1.4.4.4
		-- 1.3.6.1.4.1.37950.1.1.6.2.1.4.4.4
		linePGemCos OBJECT-TYPE
			SYNTAX Integer32 (0..8)
			MAX-ACCESS read-write
			STATUS current
			DESCRIPTION
				"Description."
			::= { linePGemport 4 }

		
--  1.3.6.1.4.1.37950.1.1.6.2.1.4.4.5
		-- 1.3.6.1.4.1.37950.1.1.6.2.1.4.4.5
		linePGemUpTraffic OBJECT-TYPE
			SYNTAX OCTET STRING
			MAX-ACCESS read-write
			STATUS current
			DESCRIPTION
				"Description."
			::= { linePGemport 5 }

		
--  1.3.6.1.4.1.37950.1.1.6.2.1.4.4.6
		-- 1.3.6.1.4.1.37950.1.1.6.2.1.4.4.6
		linePGemDnTraffic OBJECT-TYPE
			SYNTAX OCTET STRING
			MAX-ACCESS read-write
			STATUS current
			DESCRIPTION
				"Description."
			::= { linePGemport 6 }

		
--  1.3.6.1.4.1.37950.1.1.6.2.1.4.4.7
		-- 1.3.6.1.4.1.37950.1.1.6.2.1.4.4.7
		linePGemUpQMap OBJECT-TYPE
			SYNTAX Integer32 (0..4)
			MAX-ACCESS read-write
			STATUS current
			DESCRIPTION
				"Description."
			::= { linePGemport 7 }

		
--  1.3.6.1.4.1.37950.1.1.6.2.1.4.4.8
		-- 1.3.6.1.4.1.37950.1.1.6.2.1.4.4.8
		linePGemDnQMap OBJECT-TYPE
			SYNTAX Integer32 (0..8)
			MAX-ACCESS read-write
			STATUS current
			DESCRIPTION
				"Description."
			::= { linePGemport 8 }

		
--  1.3.6.1.4.1.37950.1.1.6.2.1.4.4.9
		-- 1.3.6.1.4.1.37950.1.1.6.2.1.4.4.9
		linePGemState OBJECT-TYPE
			SYNTAX INTEGER
				{
				disable(0),
				enable(1)
				}
			MAX-ACCESS read-write
			STATUS current
			DESCRIPTION
				"Description."
			::= { linePGemport 9 }

		
--  1.3.6.1.4.1.37950.1.1.6.2.1.4.4.10
		-- 1.3.6.1.4.1.37950.1.1.6.2.1.4.4.10
		linePGemAction OBJECT-TYPE
			SYNTAX INTEGER
				{
				add(1),
				del(2)
				}
			MAX-ACCESS read-write
			STATUS current
			DESCRIPTION
				"Description."
			::= { linePGemport 10 }

		
--  1.3.6.1.4.1.37950.1.1.6.2.1.4.5
		-- 1.3.6.1.4.1.37950.1.1.6.2.1.4.5
		linePSrv OBJECT IDENTIFIER ::= { v1600gLineProfileCfg 5 }

		
--  1.3.6.1.4.1.37950.1.1.6.2.1.4.5.1
		-- 1.3.6.1.4.1.37950.1.1.6.2.1.4.5.1
		linePSrvName OBJECT-TYPE
			SYNTAX OCTET STRING
			MAX-ACCESS read-write
			STATUS current
			DESCRIPTION
				"Description."
			::= { linePSrv 1 }

		
--  1.3.6.1.4.1.37950.1.1.6.2.1.4.5.2
		-- 1.3.6.1.4.1.37950.1.1.6.2.1.4.5.2
		linePSrvGemId OBJECT-TYPE
			SYNTAX Integer32 (1..255)
			MAX-ACCESS read-write
			STATUS current
			DESCRIPTION
				"Description."
			::= { linePSrv 2 }

		
--  1.3.6.1.4.1.37950.1.1.6.2.1.4.5.3
		-- 1.3.6.1.4.1.37950.1.1.6.2.1.4.5.3
		linePSrvVlanMode OBJECT-TYPE
			SYNTAX INTEGER
				{
				tag(1),
				untag(2)
				}
			MAX-ACCESS read-write
			STATUS current
			DESCRIPTION
				"Description."
			::= { linePSrv 3 }

		
--  1.3.6.1.4.1.37950.1.1.6.2.1.4.5.4
		-- 1.3.6.1.4.1.37950.1.1.6.2.1.4.5.4
		linePSrvVlanList OBJECT-TYPE
			SYNTAX OCTET STRING
			MAX-ACCESS read-write
			STATUS current
			DESCRIPTION
				"Description."
			::= { linePSrv 4 }

		
--  1.3.6.1.4.1.37950.1.1.6.2.1.4.5.5
		-- 1.3.6.1.4.1.37950.1.1.6.2.1.4.5.5
		linePSrvCosList OBJECT-TYPE
			SYNTAX OCTET STRING
			MAX-ACCESS read-write
			STATUS current
			DESCRIPTION
				"Description."
			::= { linePSrv 5 }

		
--  1.3.6.1.4.1.37950.1.1.6.2.1.4.5.6
		-- 1.3.6.1.4.1.37950.1.1.6.2.1.4.5.6
		linePSrvPortType OBJECT-TYPE
			SYNTAX INTEGER
				{
				null(0),
				eth(1),
				iphost(2)
				}
			MAX-ACCESS read-write
			STATUS current
			DESCRIPTION
				"Description."
			::= { linePSrv 6 }

		
--  1.3.6.1.4.1.37950.1.1.6.2.1.4.5.7
		-- 1.3.6.1.4.1.37950.1.1.6.2.1.4.5.7
		linePSrvEthuni OBJECT-TYPE
			SYNTAX Integer32
			MAX-ACCESS read-write
			STATUS current
			DESCRIPTION
				"Description."
			::= { linePSrv 7 }

		
--  1.3.6.1.4.1.37950.1.1.6.2.1.4.5.8
		-- 1.3.6.1.4.1.37950.1.1.6.2.1.4.5.8
		linePSrvIphost OBJECT-TYPE
			SYNTAX Integer32
			MAX-ACCESS read-write
			STATUS current
			DESCRIPTION
				"Description."
			::= { linePSrv 8 }

		
--  1.3.6.1.4.1.37950.1.1.6.2.1.4.5.9
		-- 1.3.6.1.4.1.37950.1.1.6.2.1.4.5.9
		linePSrvAction OBJECT-TYPE
			SYNTAX INTEGER
				{
				add(1),
				del(2)
				}
			MAX-ACCESS read-write
			STATUS current
			DESCRIPTION
				"Description."
			::= { linePSrv 9 }

		
--  1.3.6.1.4.1.37950.1.1.6.2.1.4.6
		-- 1.3.6.1.4.1.37950.1.1.6.2.1.4.6
		linePSrvPort OBJECT IDENTIFIER ::= { v1600gLineProfileCfg 6 }

		
--  1.3.6.1.4.1.37950.1.1.6.2.1.4.6.1
		-- 1.3.6.1.4.1.37950.1.1.6.2.1.4.6.1
		linePSrvPortMode OBJECT-TYPE
			SYNTAX INTEGER
				{
				cvlan(1),
				cvlanEtype(2),
				cvlanUserdefinedEtype(3),
				cvlanPriority(4),
				cvlanRangeTransparent(5),
				untagged(6),
				untaggedEtype(7),
				untaggedUserdefinedEtype(8)
				}
			MAX-ACCESS read-write
			STATUS current
			DESCRIPTION
				"Description."
			::= { linePSrvPort 1 }

		
--  1.3.6.1.4.1.37950.1.1.6.2.1.4.6.2
		-- 1.3.6.1.4.1.37950.1.1.6.2.1.4.6.2
		linePSrvPortId OBJECT-TYPE
			SYNTAX Integer32 (1..128)
			MAX-ACCESS read-write
			STATUS current
			DESCRIPTION
				"Description."
			::= { linePSrvPort 2 }

		
--  1.3.6.1.4.1.37950.1.1.6.2.1.4.6.3
		-- 1.3.6.1.4.1.37950.1.1.6.2.1.4.6.3
		linePSrvPortGemId OBJECT-TYPE
			SYNTAX Integer32
			MAX-ACCESS read-write
			STATUS current
			DESCRIPTION
				"Description."
			::= { linePSrvPort 3 }

		
--  1.3.6.1.4.1.37950.1.1.6.2.1.4.6.4
		-- 1.3.6.1.4.1.37950.1.1.6.2.1.4.6.4
		linePSrvPortUserVlan OBJECT-TYPE
			SYNTAX Integer32 (0..4093)
			MAX-ACCESS read-write
			STATUS current
			DESCRIPTION
				"Description."
			::= { linePSrvPort 4 }

		
--  1.3.6.1.4.1.37950.1.1.6.2.1.4.6.5
		-- 1.3.6.1.4.1.37950.1.1.6.2.1.4.6.5
		linePSrvPortTslVlan OBJECT-TYPE
			SYNTAX Integer32 (0..4093)
			MAX-ACCESS read-write
			STATUS current
			DESCRIPTION
				"Description."
			::= { linePSrvPort 5 }

		
--  1.3.6.1.4.1.37950.1.1.6.2.1.4.6.6
		-- 1.3.6.1.4.1.37950.1.1.6.2.1.4.6.6
		linePSrvPortTslCos OBJECT-TYPE
			SYNTAX Integer32 (-1..7)
			MAX-ACCESS read-write
			STATUS current
			DESCRIPTION
				"Description."
			::= { linePSrvPort 6 }

		
--  1.3.6.1.4.1.37950.1.1.6.2.1.4.6.7
		-- 1.3.6.1.4.1.37950.1.1.6.2.1.4.6.7
		linePSrvPortTslSvlan OBJECT-TYPE
			SYNTAX Integer32 (0..4093)
			MAX-ACCESS read-write
			STATUS current
			DESCRIPTION
				"Description."
			::= { linePSrvPort 7 }

		
--  1.3.6.1.4.1.37950.1.1.6.2.1.4.6.8
		-- 1.3.6.1.4.1.37950.1.1.6.2.1.4.6.8
		linePSrvPortTslScos OBJECT-TYPE
			SYNTAX Integer32 (-1..7)
			MAX-ACCESS read-write
			STATUS current
			DESCRIPTION
				"Description."
			::= { linePSrvPort 8 }

		
--  1.3.6.1.4.1.37950.1.1.6.2.1.4.6.9
		-- 1.3.6.1.4.1.37950.1.1.6.2.1.4.6.9
		linePSrvPortDesc OBJECT-TYPE
			SYNTAX OCTET STRING
			MAX-ACCESS read-write
			STATUS current
			DESCRIPTION
				"Description."
			::= { linePSrvPort 9 }

		
--  1.3.6.1.4.1.37950.1.1.6.2.1.4.6.10
		-- 1.3.6.1.4.1.37950.1.1.6.2.1.4.6.10
		linePSrvPortEtype OBJECT-TYPE
			SYNTAX INTEGER
				{
				pppoe(1),
				ipoe(2)
				}
			MAX-ACCESS read-write
			STATUS current
			DESCRIPTION
				"Description."
			::= { linePSrvPort 10 }

		
--  1.3.6.1.4.1.37950.1.1.6.2.1.4.6.11
		-- 1.3.6.1.4.1.37950.1.1.6.2.1.4.6.11
		linePSrvPortUserEtype OBJECT-TYPE
			SYNTAX OCTET STRING
			MAX-ACCESS read-write
			STATUS current
			DESCRIPTION
				"Description."
			::= { linePSrvPort 11 }

		
--  1.3.6.1.4.1.37950.1.1.6.2.1.4.6.12
		-- 1.3.6.1.4.1.37950.1.1.6.2.1.4.6.12
		linePSrvPortUserPri OBJECT-TYPE
			SYNTAX Integer32 (0..7)
			MAX-ACCESS read-write
			STATUS current
			DESCRIPTION
				"Description."
			::= { linePSrvPort 12 }

		
--  1.3.6.1.4.1.37950.1.1.6.2.1.4.6.13
		-- 1.3.6.1.4.1.37950.1.1.6.2.1.4.6.13
		linePSrvPortBeginVid OBJECT-TYPE
			SYNTAX Integer32 (0..4093)
			MAX-ACCESS read-write
			STATUS current
			DESCRIPTION
				"Description."
			::= { linePSrvPort 13 }

		
--  1.3.6.1.4.1.37950.1.1.6.2.1.4.6.14
		-- 1.3.6.1.4.1.37950.1.1.6.2.1.4.6.14
		linePSrvPortEndVid OBJECT-TYPE
			SYNTAX Integer32 (0..4093)
			MAX-ACCESS read-write
			STATUS current
			DESCRIPTION
				"Description."
			::= { linePSrvPort 14 }

		
--  1.3.6.1.4.1.37950.1.1.6.2.1.4.6.15
		-- 1.3.6.1.4.1.37950.1.1.6.2.1.4.6.15
		linePSrvPortAction OBJECT-TYPE
			SYNTAX INTEGER
				{
				add(1),
				del(2)
				}
			MAX-ACCESS read-write
			STATUS current
			DESCRIPTION
				"Description."
			::= { linePSrvPort 15 }

		
--  1.3.6.1.4.1.37950.1.1.6.2.1.4.7
		-- 1.3.6.1.4.1.37950.1.1.6.2.1.4.7
		linePMVlan OBJECT IDENTIFIER ::= { v1600gLineProfileCfg 7 }

		
--  1.3.6.1.4.1.37950.1.1.6.2.1.4.7.1
		-- 1.3.6.1.4.1.37950.1.1.6.2.1.4.7.1
		linePMVlanList OBJECT-TYPE
			SYNTAX OCTET STRING
			MAX-ACCESS read-write
			STATUS current
			DESCRIPTION
				"Description."
			::= { linePMVlan 1 }

		
--  1.3.6.1.4.1.37950.1.1.6.2.1.4.7.2
		-- 1.3.6.1.4.1.37950.1.1.6.2.1.4.7.2
		linePMVlanListAction OBJECT-TYPE
			SYNTAX INTEGER
				{
				add(1),
				del(2)
				}
			MAX-ACCESS read-write
			STATUS current
			DESCRIPTION
				"Description."
			::= { linePMVlan 2 }

		
--  1.3.6.1.4.1.37950.1.1.6.2.1.5
		-- 1.3.6.1.4.1.37950.1.1.6.2.1.5
		v1600gSrvProfileCfg OBJECT IDENTIFIER ::= { v1600gProfileCfg 5 }

		
--  1.3.6.1.4.1.37950.1.1.6.2.1.5.1
		-- 1.3.6.1.4.1.37950.1.1.6.2.1.5.1
		srvPName OBJECT-TYPE
			SYNTAX OCTET STRING
			MAX-ACCESS read-write
			STATUS current
			DESCRIPTION
				"Description."
			::= { v1600gSrvProfileCfg 1 }

		
--  1.3.6.1.4.1.37950.1.1.6.2.1.5.2
		-- 1.3.6.1.4.1.37950.1.1.6.2.1.5.2
		srvPNameAction OBJECT-TYPE
			SYNTAX INTEGER
				{
				add(1),
				del(2),
				commit(3)
				}
			MAX-ACCESS read-write
			STATUS current
			DESCRIPTION
				"Description."
			::= { v1600gSrvProfileCfg 2 }

		
--  1.3.6.1.4.1.37950.1.1.6.2.1.5.3
		-- 1.3.6.1.4.1.37950.1.1.6.2.1.5.3
		srvPPortVlan OBJECT IDENTIFIER ::= { v1600gSrvProfileCfg 3 }

		
--  1.3.6.1.4.1.37950.1.1.6.2.1.5.3.1
		-- 1.3.6.1.4.1.37950.1.1.6.2.1.5.3.1
		srvPPortVlanType OBJECT-TYPE
			SYNTAX INTEGER
				{
				transparent(1),
				trunk(2),
				tag(3),
				hybrid(4),
				translate(5)
				}
			MAX-ACCESS read-write
			STATUS current
			DESCRIPTION
				"Description."
			::= { srvPPortVlan 1 }

		
--  1.3.6.1.4.1.37950.1.1.6.2.1.5.3.2
		-- 1.3.6.1.4.1.37950.1.1.6.2.1.5.3.2
		srvPPortVlanPort OBJECT-TYPE
			SYNTAX INTEGER
				{
				eth(1),
				wifi(2),
				veip(3)
				}
			MAX-ACCESS read-write
			STATUS current
			DESCRIPTION
				"Description."
			::= { srvPPortVlan 2 }

		
--  1.3.6.1.4.1.37950.1.1.6.2.1.5.3.3
		-- 1.3.6.1.4.1.37950.1.1.6.2.1.5.3.3
		srvPPortVlanPortId OBJECT-TYPE
			SYNTAX Integer32 (1..32)
			MAX-ACCESS read-write
			STATUS current
			DESCRIPTION
				"Description."
			::= { srvPPortVlan 3 }

		
--  1.3.6.1.4.1.37950.1.1.6.2.1.5.3.4
		-- 1.3.6.1.4.1.37950.1.1.6.2.1.5.3.4
		srvPPortVlanVlan OBJECT-TYPE
			SYNTAX Integer32 (1..4094)
			MAX-ACCESS read-write
			STATUS current
			DESCRIPTION
				"Description."
			::= { srvPPortVlan 4 }

		
--  1.3.6.1.4.1.37950.1.1.6.2.1.5.3.5
		-- 1.3.6.1.4.1.37950.1.1.6.2.1.5.3.5
		srvPPortVlanVlanList OBJECT-TYPE
			SYNTAX OCTET STRING
			MAX-ACCESS read-write
			STATUS current
			DESCRIPTION
				"Description."
			::= { srvPPortVlan 5 }

		
--  1.3.6.1.4.1.37950.1.1.6.2.1.5.3.6
		-- 1.3.6.1.4.1.37950.1.1.6.2.1.5.3.6
		srvPPortVlanTPri OBJECT-TYPE
			SYNTAX Integer32 (0..8)
			MAX-ACCESS read-write
			STATUS current
			DESCRIPTION
				"Description."
			::= { srvPPortVlan 6 }

		
--  1.3.6.1.4.1.37950.1.1.6.2.1.5.3.7
		-- 1.3.6.1.4.1.37950.1.1.6.2.1.5.3.7
		srvPPortVlanDefVid OBJECT-TYPE
			SYNTAX Integer32 (1..4094)
			MAX-ACCESS read-write
			STATUS current
			DESCRIPTION
				"Description."
			::= { srvPPortVlan 7 }

		
--  1.3.6.1.4.1.37950.1.1.6.2.1.5.3.8
		-- 1.3.6.1.4.1.37950.1.1.6.2.1.5.3.8
		srvPPortVlanDefpri OBJECT-TYPE
			SYNTAX Integer32 (0..8)
			MAX-ACCESS read-write
			STATUS current
			DESCRIPTION
				"Description."
			::= { srvPPortVlan 8 }

		
--  1.3.6.1.4.1.37950.1.1.6.2.1.5.3.9
		-- 1.3.6.1.4.1.37950.1.1.6.2.1.5.3.9
		srvPPortVlanTransCVid OBJECT-TYPE
			SYNTAX Integer32 (1..4094)
			MAX-ACCESS read-write
			STATUS current
			DESCRIPTION
				"Description."
			::= { srvPPortVlan 9 }

		
--  1.3.6.1.4.1.37950.1.1.6.2.1.5.3.10
		-- 1.3.6.1.4.1.37950.1.1.6.2.1.5.3.10
		srvPPortVlanTransCPri OBJECT-TYPE
			SYNTAX Integer32 (0..8)
			MAX-ACCESS read-write
			STATUS current
			DESCRIPTION
				"Description."
			::= { srvPPortVlan 10 }

		
--  1.3.6.1.4.1.37950.1.1.6.2.1.5.3.11
		-- 1.3.6.1.4.1.37950.1.1.6.2.1.5.3.11
		srvPPortVlanTransSVid OBJECT-TYPE
			SYNTAX Integer32 (1..4094)
			MAX-ACCESS read-write
			STATUS current
			DESCRIPTION
				"Description."
			::= { srvPPortVlan 11 }

		
--  1.3.6.1.4.1.37950.1.1.6.2.1.5.3.12
		-- 1.3.6.1.4.1.37950.1.1.6.2.1.5.3.12
		srvPPortVlanTransSPri OBJECT-TYPE
			SYNTAX Integer32 (0..8)
			MAX-ACCESS read-write
			STATUS current
			DESCRIPTION
				"Description."
			::= { srvPPortVlan 12 }

		
--  1.3.6.1.4.1.37950.1.1.6.2.1.5.3.13
		-- 1.3.6.1.4.1.37950.1.1.6.2.1.5.3.13
		srvPPortVlanAction OBJECT-TYPE
			SYNTAX INTEGER
				{
				add(1),
				del(2)
				}
			MAX-ACCESS read-write
			STATUS current
			DESCRIPTION
				"Description."
			::= { srvPPortVlan 13 }

		
--  1.3.6.1.4.1.37950.1.1.6.2.1.5.4
		-- 1.3.6.1.4.1.37950.1.1.6.2.1.5.4
		srvPMVlanStrip OBJECT IDENTIFIER ::= { v1600gSrvProfileCfg 4 }

		
--  1.3.6.1.4.1.37950.1.1.6.2.1.5.4.1
		-- 1.3.6.1.4.1.37950.1.1.6.2.1.5.4.1
		srvPMVlanStripPortId OBJECT-TYPE
			SYNTAX Integer32 (1..32)
			MAX-ACCESS read-write
			STATUS current
			DESCRIPTION
				"Description."
			::= { srvPMVlanStrip 1 }

		
--  1.3.6.1.4.1.37950.1.1.6.2.1.5.4.2
		-- 1.3.6.1.4.1.37950.1.1.6.2.1.5.4.2
		srvPMVlanStripAction OBJECT-TYPE
			SYNTAX INTEGER
				{
				add(1),
				del(2)
				}
			MAX-ACCESS read-write
			STATUS current
			DESCRIPTION
				"Description."
			::= { srvPMVlanStrip 2 }

		
--  1.3.6.1.4.1.37950.1.1.6.2.1.5.5
		-- 1.3.6.1.4.1.37950.1.1.6.2.1.5.5
		srvPIphost OBJECT IDENTIFIER ::= { v1600gSrvProfileCfg 5 }

		
--  1.3.6.1.4.1.37950.1.1.6.2.1.5.5.1
		-- 1.3.6.1.4.1.37950.1.1.6.2.1.5.5.1
		srvPIphostId OBJECT-TYPE
			SYNTAX Integer32 (1..255)
			MAX-ACCESS read-write
			STATUS current
			DESCRIPTION
				"Description."
			::= { srvPIphost 1 }

		
--  1.3.6.1.4.1.37950.1.1.6.2.1.5.5.2
		-- 1.3.6.1.4.1.37950.1.1.6.2.1.5.5.2
		srvPIphostDesc OBJECT-TYPE
			SYNTAX OCTET STRING
			MAX-ACCESS read-write
			STATUS current
			DESCRIPTION
				"Description."
			::= { srvPIphost 2 }

		
--  1.3.6.1.4.1.37950.1.1.6.2.1.5.5.3
		-- 1.3.6.1.4.1.37950.1.1.6.2.1.5.5.3
		srvPIphostMode OBJECT-TYPE
			SYNTAX INTEGER
				{
				dhcp(1),
				staticIp(2)
				}
			MAX-ACCESS read-write
			STATUS current
			DESCRIPTION
				"Description."
			::= { srvPIphost 3 }

		
--  1.3.6.1.4.1.37950.1.1.6.2.1.5.5.4
		-- 1.3.6.1.4.1.37950.1.1.6.2.1.5.5.4
		srvPIphostIpaddr OBJECT-TYPE
			SYNTAX IpAddress
			MAX-ACCESS read-write
			STATUS current
			DESCRIPTION
				"Description."
			::= { srvPIphost 4 }

		
--  1.3.6.1.4.1.37950.1.1.6.2.1.5.5.5
		-- 1.3.6.1.4.1.37950.1.1.6.2.1.5.5.5
		srvPIphostMask OBJECT-TYPE
			SYNTAX IpAddress
			MAX-ACCESS read-write
			STATUS current
			DESCRIPTION
				"Description."
			::= { srvPIphost 5 }

		
--  1.3.6.1.4.1.37950.1.1.6.2.1.5.5.6
		-- 1.3.6.1.4.1.37950.1.1.6.2.1.5.5.6
		srvPIphostGateway OBJECT-TYPE
			SYNTAX IpAddress
			MAX-ACCESS read-write
			STATUS current
			DESCRIPTION
				"Description."
			::= { srvPIphost 6 }

		
--  1.3.6.1.4.1.37950.1.1.6.2.1.5.5.7
		-- 1.3.6.1.4.1.37950.1.1.6.2.1.5.5.7
		srvPIphostPriDns OBJECT-TYPE
			SYNTAX IpAddress
			MAX-ACCESS read-write
			STATUS current
			DESCRIPTION
				"Description."
			::= { srvPIphost 7 }

		
--  1.3.6.1.4.1.37950.1.1.6.2.1.5.5.8
		-- 1.3.6.1.4.1.37950.1.1.6.2.1.5.5.8
		srvPIphostSecDns OBJECT-TYPE
			SYNTAX IpAddress
			MAX-ACCESS read-write
			STATUS current
			DESCRIPTION
				"Description."
			::= { srvPIphost 8 }

		
--  1.3.6.1.4.1.37950.1.1.6.2.1.5.5.9
		-- 1.3.6.1.4.1.37950.1.1.6.2.1.5.5.9
		srvPIphostAction OBJECT-TYPE
			SYNTAX INTEGER
				{
				add(1),
				del(2)
				}
			MAX-ACCESS read-write
			STATUS current
			DESCRIPTION
				"Description."
			::= { srvPIphost 9 }

		
--  1.3.6.1.4.1.37950.1.1.6.2.1.5.6
		-- 1.3.6.1.4.1.37950.1.1.6.2.1.5.6
		gSrvPIphostVlanConfig OBJECT IDENTIFIER ::= { v1600gSrvProfileCfg 6 }

		
--  1.3.6.1.4.1.37950.1.1.6.2.1.5.6.1
		-- 1.3.6.1.4.1.37950.1.1.6.2.1.5.6.1
		gSrvPIphostVlan OBJECT-TYPE
			SYNTAX Integer32 (1..4094)
			MAX-ACCESS read-write
			STATUS current
			DESCRIPTION
				"Description."
			::= { gSrvPIphostVlanConfig 1 }

		
--  1.3.6.1.4.1.37950.1.1.6.2.1.5.6.2
		-- 1.3.6.1.4.1.37950.1.1.6.2.1.5.6.2
		gSrvPIphostVlanPri OBJECT-TYPE
			SYNTAX Integer32 (1..15)
			MAX-ACCESS read-write
			STATUS current
			DESCRIPTION
				"Description."
			::= { gSrvPIphostVlanConfig 2 }

		
--  1.3.6.1.4.1.37950.1.1.6.2.1.5.6.3
		-- 1.3.6.1.4.1.37950.1.1.6.2.1.5.6.3
		gSrvPIphostVlanAction OBJECT-TYPE
			SYNTAX INTEGER { commit(1) }
			MAX-ACCESS read-write
			STATUS current
			DESCRIPTION
				"Description."
			::= { gSrvPIphostVlanConfig 3 }

		
		-- 1.3.6.1.4.1.37950.1.1.6.2.1.5.6.4
		gSrvPIphostVlanIphostId OBJECT-TYPE
			SYNTAX Integer32
			MAX-ACCESS read-write
			STATUS current
			DESCRIPTION
				"Description."
			::= { gSrvPIphostVlanConfig 4 }

		
--  1.3.6.1.4.1.37950.1.1.6.2.1.5.7
		-- 1.3.6.1.4.1.37950.1.1.6.2.1.5.7
		gSrvPPortBasicConfig OBJECT IDENTIFIER ::= { v1600gSrvProfileCfg 7 }

		
--  1.3.6.1.4.1.37950.1.1.6.2.1.5.7.1
		-- 1.3.6.1.4.1.37950.1.1.6.2.1.5.7.1
		gSrvPPortId OBJECT-TYPE
			SYNTAX Integer32 (1..32)
			MAX-ACCESS read-write
			STATUS current
			DESCRIPTION
				"Description."
			::= { gSrvPPortBasicConfig 1 }

		
--  1.3.6.1.4.1.37950.1.1.6.2.1.5.7.2
		-- 1.3.6.1.4.1.37950.1.1.6.2.1.5.7.2
		gSrvPPortState OBJECT-TYPE
			SYNTAX INTEGER
				{
				disable(0),
				enable(1)
				}
			MAX-ACCESS read-write
			STATUS current
			DESCRIPTION
				"Description."
			::= { gSrvPPortBasicConfig 2 }

		
--  1.3.6.1.4.1.37950.1.1.6.2.1.5.7.3
		-- 1.3.6.1.4.1.37950.1.1.6.2.1.5.7.3
		gSrvPPortMacLimit OBJECT-TYPE
			SYNTAX Integer32 (0..255)
			MAX-ACCESS read-write
			STATUS current
			DESCRIPTION
				"Description."
			::= { gSrvPPortBasicConfig 3 }

		
--  1.3.6.1.4.1.37950.1.1.6.2.1.5.7.4
		-- 1.3.6.1.4.1.37950.1.1.6.2.1.5.7.4
		gSrvPPortPauseTime OBJECT-TYPE
			SYNTAX Integer32 (0..65535)
			MAX-ACCESS read-write
			STATUS current
			DESCRIPTION
				"Description."
			::= { gSrvPPortBasicConfig 4 }

		
--  1.3.6.1.4.1.37950.1.1.6.2.1.5.7.5
		-- 1.3.6.1.4.1.37950.1.1.6.2.1.5.7.5
		gSrvPPortSpeed OBJECT-TYPE
			SYNTAX INTEGER
				{
				auto(0),
				full-10(1),
				full-100(2),
				full-1000(3),
				full-10g(5),
				full-2point5g(6),
				full-5g(7),
				full-25g(8),
				full-40g(9),
				half-10(17),
				half-100(18),
				half-1000(19)
				}
			MAX-ACCESS read-write
			STATUS current
			DESCRIPTION
				"Description."
			::= { gSrvPPortBasicConfig 5 }

		
--  1.3.6.1.4.1.37950.1.1.6.2.1.5.7.6
		-- 1.3.6.1.4.1.37950.1.1.6.2.1.5.7.6
		gSrvPPortLoopback OBJECT-TYPE
			SYNTAX INTEGER
				{
				disable(0),
				enable(1)
				}
			MAX-ACCESS read-write
			STATUS current
			DESCRIPTION
				"Description."
			::= { gSrvPPortBasicConfig 6 }

		
--  1.3.6.1.4.1.37950.1.1.6.2.1.5.7.7
		-- 1.3.6.1.4.1.37950.1.1.6.2.1.5.7.7
		gSrvPPortAction OBJECT-TYPE
			SYNTAX INTEGER
				{
				commit(1),
				delete(2)
				}
			MAX-ACCESS read-write
			STATUS current
			DESCRIPTION
				"Description."
			::= { gSrvPPortBasicConfig 7 }

		
--  1.3.6.1.4.1.37950.1.1.6.2.1.5.8
		-- 1.3.6.1.4.1.37950.1.1.6.2.1.5.8
		gSrvPPortUpstreamRateLimitConfig OBJECT IDENTIFIER ::= { v1600gSrvProfileCfg 8 }

		
--  1.3.6.1.4.1.37950.1.1.6.2.1.5.8.1
		-- 1.3.6.1.4.1.37950.1.1.6.2.1.5.8.1
		gSrvPPortUpstreamRateLimitPortId OBJECT-TYPE
			SYNTAX Integer32 (1..32)
			MAX-ACCESS read-write
			STATUS current
			DESCRIPTION
				"Description."
			::= { gSrvPPortUpstreamRateLimitConfig 1 }

		
--  1.3.6.1.4.1.37950.1.1.6.2.1.5.8.2
		-- 1.3.6.1.4.1.37950.1.1.6.2.1.5.8.2
		gSrvPPortUpstreamRateLimitCir OBJECT-TYPE
			SYNTAX INTEGER (0..33554431)
			MAX-ACCESS read-write
			STATUS current
			DESCRIPTION
				"Description."
			::= { gSrvPPortUpstreamRateLimitConfig 2 }

		
--  1.3.6.1.4.1.37950.1.1.6.2.1.5.8.3
		-- 1.3.6.1.4.1.37950.1.1.6.2.1.5.8.3
		gSrvPPortUpstreamRateLimitPir OBJECT-TYPE
			SYNTAX INTEGER (0..33554431)
			MAX-ACCESS read-write
			STATUS current
			DESCRIPTION
				"Description."
			::= { gSrvPPortUpstreamRateLimitConfig 3 }

		
--  1.3.6.1.4.1.37950.1.1.6.2.1.5.8.4
		-- 1.3.6.1.4.1.37950.1.1.6.2.1.5.8.4
		gSrvPPortUpstreamRateLimitAction OBJECT-TYPE
			SYNTAX INTEGER { commit(1) }
			MAX-ACCESS read-write
			STATUS current
			DESCRIPTION
				"Description."
			::= { gSrvPPortUpstreamRateLimitConfig 4 }

		
--  1.3.6.1.4.1.37950.1.1.6.2.1.5.9
		-- 1.3.6.1.4.1.37950.1.1.6.2.1.5.9
		gSrvPPortDownstreamRateLimitConfig OBJECT IDENTIFIER ::= { v1600gSrvProfileCfg 9 }

		
--  1.3.6.1.4.1.37950.1.1.6.2.1.5.9.1
		-- 1.3.6.1.4.1.37950.1.1.6.2.1.5.9.1
		gSrvPPortDownstreamRateLimitPortId OBJECT-TYPE
			SYNTAX Integer32 (1..32)
			MAX-ACCESS read-write
			STATUS current
			DESCRIPTION
				"Description."
			::= { gSrvPPortDownstreamRateLimitConfig 1 }

		
--  1.3.6.1.4.1.37950.1.1.6.2.1.5.9.2
		-- 1.3.6.1.4.1.37950.1.1.6.2.1.5.9.2
		gSrvPPortDownstreamRateLimitCir OBJECT-TYPE
			SYNTAX INTEGER (0..33554431)
			MAX-ACCESS read-write
			STATUS current
			DESCRIPTION
				"Description."
			::= { gSrvPPortDownstreamRateLimitConfig 2 }

		
--  1.3.6.1.4.1.37950.1.1.6.2.1.5.9.3
		-- 1.3.6.1.4.1.37950.1.1.6.2.1.5.9.3
		gSrvPPortDownstreamRateLimitPir OBJECT-TYPE
			SYNTAX INTEGER (0..33554431)
			MAX-ACCESS read-write
			STATUS current
			DESCRIPTION
				"Description."
			::= { gSrvPPortDownstreamRateLimitConfig 3 }

		
--  1.3.6.1.4.1.37950.1.1.6.2.1.5.9.4
		-- 1.3.6.1.4.1.37950.1.1.6.2.1.5.9.4
		gSrvPPortDownstreamRateLimitAction OBJECT-TYPE
			SYNTAX INTEGER { commit(1) }
			MAX-ACCESS read-write
			STATUS current
			DESCRIPTION
				"Description."
			::= { gSrvPPortDownstreamRateLimitConfig 4 }

		
--  1.3.6.1.4.1.37950.1.1.6.2.1.6
		-- 1.3.6.1.4.1.37950.1.1.6.2.1.6
		v1600gAlarmProfileCfg OBJECT IDENTIFIER ::= { v1600gProfileCfg 6 }

		
--  1.3.6.1.4.1.37950.1.1.6.2.1.6.1
		-- 1.3.6.1.4.1.37950.1.1.6.2.1.6.1
		alarmPName OBJECT-TYPE
			SYNTAX OCTET STRING
			MAX-ACCESS read-write
			STATUS current
			DESCRIPTION
				"Description."
			::= { v1600gAlarmProfileCfg 1 }

		
--  1.3.6.1.4.1.37950.1.1.6.2.1.6.2
		-- 1.3.6.1.4.1.37950.1.1.6.2.1.6.2
		alarmPState OBJECT-TYPE
			SYNTAX INTEGER
				{
				disable(0),
				enable(1)
				}
			MAX-ACCESS read-write
			STATUS current
			DESCRIPTION
				"Description."
			::= { v1600gAlarmProfileCfg 2 }

		
--  1.3.6.1.4.1.37950.1.1.6.2.1.6.3
		-- 1.3.6.1.4.1.37950.1.1.6.2.1.6.3
		alarmPRxLow OBJECT-TYPE
			SYNTAX Integer32 (-27..-8)
			MAX-ACCESS read-write
			STATUS current
			DESCRIPTION
				"Description."
			::= { v1600gAlarmProfileCfg 3 }

		
--  1.3.6.1.4.1.37950.1.1.6.2.1.6.4
		-- 1.3.6.1.4.1.37950.1.1.6.2.1.6.4
		alarmPRxHigh OBJECT-TYPE
			SYNTAX Integer32 (-27..-8)
			MAX-ACCESS read-write
			STATUS current
			DESCRIPTION
				"Description."
			::= { v1600gAlarmProfileCfg 4 }

		
--  1.3.6.1.4.1.37950.1.1.6.2.1.6.5
		-- 1.3.6.1.4.1.37950.1.1.6.2.1.6.5
		alarmPTxLow OBJECT-TYPE
			SYNTAX Integer32 (0..5)
			MAX-ACCESS read-write
			STATUS current
			DESCRIPTION
				"Description."
			::= { v1600gAlarmProfileCfg 5 }

		
--  1.3.6.1.4.1.37950.1.1.6.2.1.6.6
		-- 1.3.6.1.4.1.37950.1.1.6.2.1.6.6
		alarmPTxHigh OBJECT-TYPE
			SYNTAX Integer32 (0..10)
			MAX-ACCESS read-write
			STATUS current
			DESCRIPTION
				"Description."
			::= { v1600gAlarmProfileCfg 6 }

		
--  1.3.6.1.4.1.37950.1.1.6.2.1.6.7
		-- 1.3.6.1.4.1.37950.1.1.6.2.1.6.7
		alarmPSF OBJECT-TYPE
			SYNTAX Integer32 (3..8)
			MAX-ACCESS read-write
			STATUS current
			DESCRIPTION
				"Description."
			::= { v1600gAlarmProfileCfg 7 }

		
--  1.3.6.1.4.1.37950.1.1.6.2.1.6.8
		-- 1.3.6.1.4.1.37950.1.1.6.2.1.6.8
		alarmPSD OBJECT-TYPE
			SYNTAX Integer32 (4..10)
			MAX-ACCESS read-write
			STATUS current
			DESCRIPTION
				"Description."
			::= { v1600gAlarmProfileCfg 8 }

		
--  1.3.6.1.4.1.37950.1.1.6.2.1.6.9
		-- 1.3.6.1.4.1.37950.1.1.6.2.1.6.9
		alarmPAction OBJECT-TYPE
			SYNTAX INTEGER
				{
				add(1),
				del(2),
				commit(3)
				}
			MAX-ACCESS read-write
			STATUS current
			DESCRIPTION
				"Description."
			::= { v1600gAlarmProfileCfg 9 }

		
--   1.3.6.1.4.1.37950.1.1.5.12.8.6
-- 1.3.6.1.4.1.37950.1.1.6.2.1.7
		-- 1.3.6.1.4.1.37950.1.1.6.2.1.7
		v1600gProfileManualBind OBJECT IDENTIFIER ::= { v1600gProfileCfg 7 }

		
--   1.3.6.1.4.1.37950.1.1.5.12.8.6.1
-- 1.3.6.1.4.1.37950.1.1.6.2.1.7.1
		-- 1.3.6.1.4.1.37950.1.1.6.2.1.7.1
		profileManualBindPon OBJECT-TYPE
			SYNTAX Integer32
			MAX-ACCESS read-write
			STATUS current
			DESCRIPTION
				"Description."
			::= { v1600gProfileManualBind 1 }

		
--   1.3.6.1.4.1.37950.1.1.5.12.8.6.3
-- 1.3.6.1.4.1.37950.1.1.6.2.1.7.2
		-- 1.3.6.1.4.1.37950.1.1.6.2.1.7.2
		profileManualBindOnu OBJECT-TYPE
			SYNTAX Integer32 (1..65535)
			MAX-ACCESS read-write
			STATUS current
			DESCRIPTION
				"Description."
			::= { v1600gProfileManualBind 2 }

		
--   1.3.6.1.4.1.37950.1.1.5.12.8.6.4
-- 1.3.6.1.4.1.37950.1.1.6.2.1.7.3
		-- 1.3.6.1.4.1.37950.1.1.6.2.1.7.3
		profileManualBindLineName OBJECT-TYPE
			SYNTAX OCTET STRING
			MAX-ACCESS read-write
			STATUS current
			DESCRIPTION
				"Description."
			::= { v1600gProfileManualBind 3 }

		
--   1.3.6.1.4.1.37950.1.1.5.12.8.6.4
-- 1.3.6.1.4.1.37950.1.1.6.2.1.7.4
		-- 1.3.6.1.4.1.37950.1.1.6.2.1.7.4
		profileManualBindSrvName OBJECT-TYPE
			SYNTAX OCTET STRING
			MAX-ACCESS read-write
			STATUS current
			DESCRIPTION
				"Description."
			::= { v1600gProfileManualBind 4 }

		
--   1.3.6.1.4.1.37950.1.1.5.12.8.6.4
-- 1.3.6.1.4.1.37950.1.1.6.2.1.7.5
		-- 1.3.6.1.4.1.37950.1.1.6.2.1.7.5
		profileManualBindAlarmName OBJECT-TYPE
			SYNTAX OCTET STRING
			MAX-ACCESS read-write
			STATUS current
			DESCRIPTION
				"Description."
			::= { v1600gProfileManualBind 5 }

		
--   1.3.6.1.4.1.37950.1.1.5.12.8.6.5
-- 1.3.6.1.4.1.37950.1.1.6.2.1.7.6
		-- 1.3.6.1.4.1.37950.1.1.6.2.1.7.6
		profileManualBindAction OBJECT-TYPE
			SYNTAX INTEGER { commit(1) }
			MAX-ACCESS read-write
			STATUS current
			DESCRIPTION
				"Description."
			::= { v1600gProfileManualBind 6 }

		
--  1.3.6.1.4.1.37950.1.1.6.2.1.7.7
		-- 1.3.6.1.4.1.37950.1.1.6.2.1.7.7
		profileManualBindPirName OBJECT-TYPE
			SYNTAX OCTET STRING
			MAX-ACCESS read-write
			STATUS current
			DESCRIPTION
				"Description."
			::= { v1600gProfileManualBind 7 }

		
--  1.3.6.1.4.1.37950.1.1.6.2.1.7.8
		-- 1.3.6.1.4.1.37950.1.1.6.2.1.7.8
		profileManualBindFmtName OBJECT-TYPE
			SYNTAX OCTET STRING
			MAX-ACCESS read-write
			STATUS current
			DESCRIPTION
				"Description."
			::= { v1600gProfileManualBind 8 }

		
--  1.3.6.1.4.1.37950.1.1.6.2.1.8
		-- 1.3.6.1.4.1.37950.1.1.6.2.1.8
		v1600gPriProfileCfg OBJECT IDENTIFIER ::= { v1600gProfileCfg 8 }

		
--  1.3.6.1.4.1.37950.1.1.6.2.1.8.1
		-- 1.3.6.1.4.1.37950.1.1.6.2.1.8.1
		priPName OBJECT-TYPE
			SYNTAX OCTET STRING
			MAX-ACCESS read-write
			STATUS current
			DESCRIPTION
				"Description."
			::= { v1600gPriProfileCfg 1 }

		
--  1.3.6.1.4.1.37950.1.1.6.2.1.8.2
		-- 1.3.6.1.4.1.37950.1.1.6.2.1.8.2
		priPNameAction OBJECT-TYPE
			SYNTAX INTEGER
				{
				add(1),
				del(2),
				commit(3)
				}
			MAX-ACCESS read-write
			STATUS current
			DESCRIPTION
				"Description."
			::= { v1600gPriProfileCfg 2 }

		
--  1.3.6.1.4.1.37950.1.1.6.2.1.8.3
		-- 1.3.6.1.4.1.37950.1.1.6.2.1.8.3
		priPWan OBJECT IDENTIFIER ::= { v1600gPriProfileCfg 3 }

		
--  1.3.6.1.4.1.37950.1.1.6.2.1.8.3.1
		-- 1.3.6.1.4.1.37950.1.1.6.2.1.8.3.1
		priPWanAdd OBJECT IDENTIFIER ::= { priPWan 1 }

		
--  1.3.6.1.4.1.37950.1.1.6.2.1.8.3.1.1
		-- 1.3.6.1.4.1.37950.1.1.6.2.1.8.3.1.1
		priPWanAddProfileID OBJECT-TYPE
			SYNTAX Integer32
			MAX-ACCESS read-write
			STATUS current
			DESCRIPTION
				"Description."
			::= { priPWanAdd 1 }

		
--  1.3.6.1.4.1.37950.1.1.6.2.1.8.3.1.2
		-- 1.3.6.1.4.1.37950.1.1.6.2.1.8.3.1.2
		priPWanAddType OBJECT-TYPE
			SYNTAX INTEGER
				{
				brige(0),
				route(1)
				}
			MAX-ACCESS read-write
			STATUS current
			DESCRIPTION
				"Description."
			::= { priPWanAdd 2 }

		
--  1.3.6.1.4.1.37950.1.1.6.2.1.8.3.1.3
		-- 1.3.6.1.4.1.37950.1.1.6.2.1.8.3.1.3
		priPWanAddAction OBJECT-TYPE
			SYNTAX INTEGER { add(1) }
			MAX-ACCESS read-write
			STATUS current
			DESCRIPTION
				"Description."
			::= { priPWanAdd 3 }

		
--  1.3.6.1.4.1.37950.1.1.6.2.1.8.3.2
		-- 1.3.6.1.4.1.37950.1.1.6.2.1.8.3.2
		priPWanDelete OBJECT IDENTIFIER ::= { priPWan 2 }

		
--  1.3.6.1.4.1.37950.1.1.6.2.1.8.3.2.1
		-- 1.3.6.1.4.1.37950.1.1.6.2.1.8.3.2.1
		priPWanDeleteProfileID OBJECT-TYPE
			SYNTAX Integer32
			MAX-ACCESS read-write
			STATUS current
			DESCRIPTION
				"Description."
			::= { priPWanDelete 1 }

		
--  1.3.6.1.4.1.37950.1.1.6.2.1.8.3.2.2
		-- 1.3.6.1.4.1.37950.1.1.6.2.1.8.3.2.2
		priPWanDeleteWanIndex OBJECT-TYPE
			SYNTAX Integer32 (1..8)
			MAX-ACCESS read-write
			STATUS current
			DESCRIPTION
				"Description."
			::= { priPWanDelete 2 }

		
--  1.3.6.1.4.1.37950.1.1.6.2.1.8.3.2.3
		-- 1.3.6.1.4.1.37950.1.1.6.2.1.8.3.2.3
		priPWanDeleteAction OBJECT-TYPE
			SYNTAX INTEGER { delete(1) }
			MAX-ACCESS read-write
			STATUS current
			DESCRIPTION
				"Description."
			::= { priPWanDelete 3 }

		
--  1.3.6.1.4.1.37950.1.1.6.2.1.8.3.3
		-- 1.3.6.1.4.1.37950.1.1.6.2.1.8.3.3
		priPWanCfg OBJECT IDENTIFIER ::= { priPWan 3 }

		
--  1.3.6.1.4.1.37950.1.1.6.2.1.8.3.3.1
		-- 1.3.6.1.4.1.37950.1.1.6.2.1.8.3.3.1
		priPWanCfgProfileID OBJECT-TYPE
			SYNTAX Integer32
			MAX-ACCESS read-write
			STATUS current
			DESCRIPTION
				"Description."
			::= { priPWanCfg 1 }

		
--  1.3.6.1.4.1.37950.1.1.6.2.1.8.3.3.2
		-- 1.3.6.1.4.1.37950.1.1.6.2.1.8.3.3.2
		priPWanCfgWanIndex OBJECT-TYPE
			SYNTAX INTEGER (1..8)
			MAX-ACCESS read-write
			STATUS current
			DESCRIPTION
				"Description."
			::= { priPWanCfg 2 }

		
--  1.3.6.1.4.1.37950.1.1.6.2.1.8.3.3.3
		-- 1.3.6.1.4.1.37950.1.1.6.2.1.8.3.3.3
		priPWanCfgBindLan OBJECT-TYPE
			SYNTAX INTEGER (0..255)
			MAX-ACCESS read-write
			STATUS current
			DESCRIPTION
				"Description."
			::= { priPWanCfg 3 }

		
--  1.3.6.1.4.1.37950.1.1.6.2.1.8.3.3.4
		-- 1.3.6.1.4.1.37950.1.1.6.2.1.8.3.3.4
		priPWanCfgBindSsid OBJECT-TYPE
			SYNTAX INTEGER (0..255)
			MAX-ACCESS read-write
			STATUS current
			DESCRIPTION
				"Description."
			::= { priPWanCfg 4 }

		
--  1.3.6.1.4.1.37950.1.1.6.2.1.8.3.3.5
		-- 1.3.6.1.4.1.37950.1.1.6.2.1.8.3.3.5
		priPWanCfgWanMode OBJECT-TYPE
			SYNTAX INTEGER
				{
				internet(0),
				multicast(1),
				tr069(2),
				tr069_internet(3),
				tr069_voip(4),
				voip_internet(5),
				tr069_voip_internet(6),
				voip(7),
				other(100)
				}
			MAX-ACCESS read-write
			STATUS current
			DESCRIPTION
				"Description."
			::= { priPWanCfg 5 }

		
--  1.3.6.1.4.1.37950.1.1.6.2.1.8.3.3.6
		-- 1.3.6.1.4.1.37950.1.1.6.2.1.8.3.3.6
		priPWanCfgTypeCfg OBJECT-TYPE
			SYNTAX INTEGER
				{
				bridge(0),
				route(1)
				}
			MAX-ACCESS read-write
			STATUS current
			DESCRIPTION
				"Description."
			::= { priPWanCfg 6 }

		
--  1.3.6.1.4.1.37950.1.1.6.2.1.8.3.3.7
		-- 1.3.6.1.4.1.37950.1.1.6.2.1.8.3.3.7
		priPWanCfgNatEnable OBJECT-TYPE
			SYNTAX INTEGER
				{
				disable(0),
				enable(1)
				}
			MAX-ACCESS read-write
			STATUS current
			DESCRIPTION
				"Description."
			::= { priPWanCfg 7 }

		
--  1.3.6.1.4.1.37950.1.1.6.2.1.8.3.3.8
		-- 1.3.6.1.4.1.37950.1.1.6.2.1.8.3.3.8
		priPWanCfgModeCfg OBJECT-TYPE
			SYNTAX INTEGER
				{
				dhcp(0),
				static(1),
				pppoe(2)
				}
			MAX-ACCESS read-write
			STATUS current
			DESCRIPTION
				"Description."
			::= { priPWanCfg 8 }

		
--  1.3.6.1.4.1.37950.1.1.6.2.1.8.3.3.9
		-- 1.3.6.1.4.1.37950.1.1.6.2.1.8.3.3.9
		priPWanCfgIpAddress OBJECT-TYPE
			SYNTAX IpAddress
			MAX-ACCESS read-write
			STATUS current
			DESCRIPTION
				"Description."
			::= { priPWanCfg 9 }

		
--  1.3.6.1.4.1.37950.1.1.6.2.1.8.3.3.10
		-- 1.3.6.1.4.1.37950.1.1.6.2.1.8.3.3.10
		priPWanCfgIpMask OBJECT-TYPE
			SYNTAX IpAddress
			MAX-ACCESS read-write
			STATUS current
			DESCRIPTION
				"Description."
			::= { priPWanCfg 10 }

		
--  1.3.6.1.4.1.37950.1.1.6.2.1.8.3.3.11
		-- 1.3.6.1.4.1.37950.1.1.6.2.1.8.3.3.11
		priPWanCfgGateway OBJECT-TYPE
			SYNTAX IpAddress
			MAX-ACCESS read-write
			STATUS current
			DESCRIPTION
				"Description."
			::= { priPWanCfg 11 }

		
--  1.3.6.1.4.1.37950.1.1.6.2.1.8.3.3.12
		-- 1.3.6.1.4.1.37950.1.1.6.2.1.8.3.3.12
		priPWanCfgMasterDns OBJECT-TYPE
			SYNTAX IpAddress
			MAX-ACCESS read-write
			STATUS current
			DESCRIPTION
				"Description."
			::= { priPWanCfg 12 }

		
--  1.3.6.1.4.1.37950.1.1.6.2.1.8.3.3.13
		-- 1.3.6.1.4.1.37950.1.1.6.2.1.8.3.3.13
		priPWanCfgSlaveDns OBJECT-TYPE
			SYNTAX IpAddress
			MAX-ACCESS read-write
			STATUS current
			DESCRIPTION
				"Description."
			::= { priPWanCfg 13 }

		
--  1.3.6.1.4.1.37950.1.1.6.2.1.8.3.3.14
		-- 1.3.6.1.4.1.37950.1.1.6.2.1.8.3.3.14
		priPWanCfgPppoeProxy OBJECT-TYPE
			SYNTAX INTEGER
				{
				disable(0),
				enable(1)
				}
			MAX-ACCESS read-write
			STATUS current
			DESCRIPTION
				"Description."
			::= { priPWanCfg 14 }

		
--  1.3.6.1.4.1.37950.1.1.6.2.1.8.3.3.15
		-- 1.3.6.1.4.1.37950.1.1.6.2.1.8.3.3.15
		priPWanCfgPppoeUsername OBJECT-TYPE
			SYNTAX OCTET STRING
			MAX-ACCESS read-write
			STATUS current
			DESCRIPTION
				"Description."
			::= { priPWanCfg 15 }

		
--  1.3.6.1.4.1.37950.1.1.6.2.1.8.3.3.16
		-- 1.3.6.1.4.1.37950.1.1.6.2.1.8.3.3.16
		priPWanCfgPppoePassword OBJECT-TYPE
			SYNTAX OCTET STRING
			MAX-ACCESS read-write
			STATUS current
			DESCRIPTION
				"Description."
			::= { priPWanCfg 16 }

		
--  1.3.6.1.4.1.37950.1.1.6.2.1.8.3.3.17
		-- 1.3.6.1.4.1.37950.1.1.6.2.1.8.3.3.17
		priPWanCfgPppoeSerName OBJECT-TYPE
			SYNTAX OCTET STRING
			MAX-ACCESS read-write
			STATUS current
			DESCRIPTION
				"Description."
			::= { priPWanCfg 17 }

		
--  1.3.6.1.4.1.37950.1.1.6.2.1.8.3.3.18
		-- 1.3.6.1.4.1.37950.1.1.6.2.1.8.3.3.18
		priPWanCfgPppoeMode OBJECT-TYPE
			SYNTAX INTEGER
				{
				autoConnect(0),
				flowConnect(1)
				}
			MAX-ACCESS read-write
			STATUS current
			DESCRIPTION
				"Description."
			::= { priPWanCfg 18 }

		
--  1.3.6.1.4.1.37950.1.1.6.2.1.8.3.3.19
		-- 1.3.6.1.4.1.37950.1.1.6.2.1.8.3.3.19
		priPWanCfgQosEnable OBJECT-TYPE
			SYNTAX INTEGER
				{
				disable(0),
				enable(1)
				}
			MAX-ACCESS read-write
			STATUS current
			DESCRIPTION
				"Description."
			::= { priPWanCfg 19 }

		
--  1.3.6.1.4.1.37950.1.1.6.2.1.8.3.3.20
		-- 1.3.6.1.4.1.37950.1.1.6.2.1.8.3.3.20
		priPWanCfgVlanMode OBJECT-TYPE
			SYNTAX INTEGER
				{
				disable(0),
				enable(1)
				}
			MAX-ACCESS read-write
			STATUS current
			DESCRIPTION
				"Description."
			::= { priPWanCfg 20 }

		
--  1.3.6.1.4.1.37950.1.1.6.2.1.8.3.3.21
		-- 1.3.6.1.4.1.37950.1.1.6.2.1.8.3.3.21
		priPWanCfgVlanId OBJECT-TYPE
			SYNTAX Integer32 (0..4095)
			MAX-ACCESS read-write
			STATUS current
			DESCRIPTION
				"Description."
			::= { priPWanCfg 21 }

		
--  1.3.6.1.4.1.37950.1.1.6.2.1.8.3.3.22
		-- 1.3.6.1.4.1.37950.1.1.6.2.1.8.3.3.22
		priPWanCfgCos OBJECT-TYPE
			SYNTAX INTEGER (0..7)
			MAX-ACCESS read-write
			STATUS current
			DESCRIPTION
				"Description."
			::= { priPWanCfg 22 }

		
--  1.3.6.1.4.1.37950.1.1.6.2.1.8.3.3.23
		-- 1.3.6.1.4.1.37950.1.1.6.2.1.8.3.3.23
		priPWanCfgAction OBJECT-TYPE
			SYNTAX INTEGER { commit(1) }
			MAX-ACCESS read-write
			STATUS current
			DESCRIPTION
				"Description."
			::= { priPWanCfg 23 }

		
--  1.3.6.1.4.1.37950.1.1.6.2.1.8.3.3.24
		-- 1.3.6.1.4.1.37950.1.1.6.2.1.8.3.3.24
		priPWanCfgMTU OBJECT-TYPE
			SYNTAX INTEGER (0 | 576..1500)
			MAX-ACCESS read-write
			STATUS current
			DESCRIPTION
				"Description."
			::= { priPWanCfg 24 }

		
--  1.3.6.1.4.1.37950.1.1.6.2.1.8.4
		-- 1.3.6.1.4.1.37950.1.1.6.2.1.8.4
		priPDhcpServer OBJECT IDENTIFIER ::= { v1600gPriProfileCfg 4 }

		
--  1.3.6.1.4.1.37950.1.1.6.2.1.8.4.1
		-- 1.3.6.1.4.1.37950.1.1.6.2.1.8.4.1
		priPDhcpServerProfileID OBJECT-TYPE
			SYNTAX Integer32
			MAX-ACCESS read-write
			STATUS current
			DESCRIPTION
				"Description."
			::= { priPDhcpServer 1 }

		
--  1.3.6.1.4.1.37950.1.1.6.2.1.8.4.2
		-- 1.3.6.1.4.1.37950.1.1.6.2.1.8.4.2
		priPDhcpLanIp OBJECT-TYPE
			SYNTAX IpAddress
			MAX-ACCESS read-write
			STATUS current
			DESCRIPTION
				"Description."
			::= { priPDhcpServer 2 }

		
--  1.3.6.1.4.1.37950.1.1.6.2.1.8.4.3
		-- 1.3.6.1.4.1.37950.1.1.6.2.1.8.4.3
		priPDhcpLanMask OBJECT-TYPE
			SYNTAX IpAddress
			MAX-ACCESS read-write
			STATUS current
			DESCRIPTION
				"Description."
			::= { priPDhcpServer 3 }

		
--  1.3.6.1.4.1.37950.1.1.6.2.1.8.4.4
		-- 1.3.6.1.4.1.37950.1.1.6.2.1.8.4.4
		priPDhcpEnable OBJECT-TYPE
			SYNTAX INTEGER
				{
				disable(0),
				enable(1),
				relay(2)
				}
			MAX-ACCESS read-write
			STATUS current
			DESCRIPTION
				"Description."
			::= { priPDhcpServer 4 }

		
--  1.3.6.1.4.1.37950.1.1.6.2.1.8.4.5
		-- 1.3.6.1.4.1.37950.1.1.6.2.1.8.4.5
		priPDhcpLease OBJECT-TYPE
			SYNTAX Unsigned32 (0..4294967295)
			MAX-ACCESS read-write
			STATUS current
			DESCRIPTION
				"Description."
			::= { priPDhcpServer 5 }

		
--  1.3.6.1.4.1.37950.1.1.6.2.1.8.4.6
		-- 1.3.6.1.4.1.37950.1.1.6.2.1.8.4.6
		priPDhcpBeginIp OBJECT-TYPE
			SYNTAX IpAddress
			MAX-ACCESS read-write
			STATUS current
			DESCRIPTION
				"Description."
			::= { priPDhcpServer 6 }

		
--  1.3.6.1.4.1.37950.1.1.6.2.1.8.4.7
		-- 1.3.6.1.4.1.37950.1.1.6.2.1.8.4.7
		priPDhcpEndIp OBJECT-TYPE
			SYNTAX IpAddress
			MAX-ACCESS read-write
			STATUS current
			DESCRIPTION
				"Description."
			::= { priPDhcpServer 7 }

		
--  1.3.6.1.4.1.37950.1.1.6.2.1.8.4.8
		-- 1.3.6.1.4.1.37950.1.1.6.2.1.8.4.8
		priPDhcpPoolType OBJECT-TYPE
			SYNTAX INTEGER
				{
				pc(0),
				camera(1),
				stb(2),
				ip_phone(3)
				}
			MAX-ACCESS read-write
			STATUS current
			DESCRIPTION
				"Description."
			::= { priPDhcpServer 8 }

		
--  1.3.6.1.4.1.37950.1.1.6.2.1.8.4.9
		-- 1.3.6.1.4.1.37950.1.1.6.2.1.8.4.9
		priPDhcpMasterDns OBJECT-TYPE
			SYNTAX IpAddress
			MAX-ACCESS read-write
			STATUS current
			DESCRIPTION
				"Description."
			::= { priPDhcpServer 9 }

		
--  1.3.6.1.4.1.37950.1.1.6.2.1.8.4.10
		-- 1.3.6.1.4.1.37950.1.1.6.2.1.8.4.10
		priPDhcpSlaveDns OBJECT-TYPE
			SYNTAX IpAddress
			MAX-ACCESS read-write
			STATUS current
			DESCRIPTION
				"Description."
			::= { priPDhcpServer 10 }

		
--  1.3.6.1.4.1.37950.1.1.6.2.1.8.4.11
		-- 1.3.6.1.4.1.37950.1.1.6.2.1.8.4.11
		priPDhcpGateway OBJECT-TYPE
			SYNTAX IpAddress
			MAX-ACCESS read-write
			STATUS current
			DESCRIPTION
				"Description."
			::= { priPDhcpServer 11 }

		
--  1.3.6.1.4.1.37950.1.1.6.2.1.8.4.12
		-- 1.3.6.1.4.1.37950.1.1.6.2.1.8.4.12
		priPDhcpRelayIp OBJECT-TYPE
			SYNTAX IpAddress
			MAX-ACCESS read-write
			STATUS current
			DESCRIPTION
				"Description."
			::= { priPDhcpServer 12 }

		
--  1.3.6.1.4.1.37950.1.1.6.2.1.8.4.13
		-- 1.3.6.1.4.1.37950.1.1.6.2.1.8.4.13
		priPDhcpAction OBJECT-TYPE
			SYNTAX INTEGER
				{
				commit(1),
				remove(2)
				}
			MAX-ACCESS read-write
			STATUS current
			DESCRIPTION
				"Description."
			::= { priPDhcpServer 13 }

		
--  1.3.6.1.4.1.37950.1.1.6.2.1.8.4.14
		-- 1.3.6.1.4.1.37950.1.1.6.2.1.8.4.14
		priPDhcpDnsMode OBJECT-TYPE
			SYNTAX INTEGER
				{
				static(0),
				hgw_proxy(1),
				from_isp(2)
				}
			MAX-ACCESS read-write
			STATUS current
			DESCRIPTION
				"Description."
			::= { priPDhcpServer 14 }

		
--  1.3.6.1.4.1.37950.1.1.6.2.1.8.5
		-- 1.3.6.1.4.1.37950.1.1.6.2.1.8.5
		priPWifiSwitch OBJECT IDENTIFIER ::= { v1600gPriProfileCfg 5 }

		
--  1.3.6.1.4.1.37950.1.1.6.2.1.8.5.1
		-- 1.3.6.1.4.1.37950.1.1.6.2.1.8.5.1
		priPWifiSwitchProfileID OBJECT-TYPE
			SYNTAX Integer32
			MAX-ACCESS read-write
			STATUS current
			DESCRIPTION
				"Description."
			::= { priPWifiSwitch 1 }

		
--  1.3.6.1.4.1.37950.1.1.6.2.1.8.5.2
		-- 1.3.6.1.4.1.37950.1.1.6.2.1.8.5.2
		priPWifiSwitchNo OBJECT-TYPE
			SYNTAX INTEGER (1..2)
			MAX-ACCESS read-write
			STATUS current
			DESCRIPTION
				"Description."
			::= { priPWifiSwitch 2 }

		
--  1.3.6.1.4.1.37950.1.1.6.2.1.8.5.3
		-- 1.3.6.1.4.1.37950.1.1.6.2.1.8.5.3
		priPWifiApModule OBJECT-TYPE
			SYNTAX INTEGER
				{
				disable(0),
				enable(1)
				}
			MAX-ACCESS read-write
			STATUS current
			DESCRIPTION
				"Description."
			::= { priPWifiSwitch 3 }

		
--  1.3.6.1.4.1.37950.1.1.6.2.1.8.5.4
		-- 1.3.6.1.4.1.37950.1.1.6.2.1.8.5.4
		priPWifiCountry OBJECT-TYPE
			SYNTAX INTEGER
				{
				etsi(0),
				fcc(1),
				ic(2),
				spain(3),
				france(4),
				mkk(5),
				isreal(6),
				mkk2(7),
				mkk3(8),
				russian(9),
				cn(10),
				global(11),
				world-wide(12),
				mkk1(13),
				ncc(14)
				}
			MAX-ACCESS read-write
			STATUS current
			DESCRIPTION
				"Description."
			::= { priPWifiSwitch 4 }

		
--  1.3.6.1.4.1.37950.1.1.6.2.1.8.5.5
		-- 1.3.6.1.4.1.37950.1.1.6.2.1.8.5.5
		priPWifiChannel OBJECT-TYPE
			SYNTAX Integer32
			MAX-ACCESS read-write
			STATUS current
			DESCRIPTION
				"Description."
			::= { priPWifiSwitch 5 }

		
--  1.3.6.1.4.1.37950.1.1.6.2.1.8.5.6
		-- 1.3.6.1.4.1.37950.1.1.6.2.1.8.5.6
		priPWifiStandard OBJECT-TYPE
			SYNTAX INTEGER
				{
				s80211b(0),
				s80211g(1),
				s80211bg(2),
				s80211n(3),
				s80211bgn(4),
				s80211ac(5),
				s80211acA(6),
				s80211acN(7),
				s80211acAN(8),
				s80211acNAC(9),
				s80211acANAC(10),
				s80211acax(11),
				s80211acANACax(12),
				s80211ax(13),
				s80211bgnax(14),
				s80211gn(15)
				}
			MAX-ACCESS read-write
			STATUS current
			DESCRIPTION
				"Description."
			::= { priPWifiSwitch 6 }

		
--  1.3.6.1.4.1.37950.1.1.6.2.1.8.5.7
		-- 1.3.6.1.4.1.37950.1.1.6.2.1.8.5.7
		priPWifiPower OBJECT-TYPE
			SYNTAX INTEGER (0..20)
			MAX-ACCESS read-write
			STATUS current
			DESCRIPTION
				"Description."
			::= { priPWifiSwitch 7 }

		
--  1.3.6.1.4.1.37950.1.1.6.2.1.8.5.8
		-- 1.3.6.1.4.1.37950.1.1.6.2.1.8.5.8
		priPWifiSwitchAction OBJECT-TYPE
			SYNTAX INTEGER
				{
				commit(1),
				remove(2)
				}
			MAX-ACCESS read-write
			STATUS current
			DESCRIPTION
				"Description."
			::= { priPWifiSwitch 8 }

		
--  1.3.6.1.4.1.37950.1.1.6.2.1.8.5.9
		-- 1.3.6.1.4.1.37950.1.1.6.2.1.8.5.9
		priPWifiChannelWidth OBJECT-TYPE
			SYNTAX INTEGER
				{
				s20MHz(0),
				s40MHz(1),
				s80MHz(2),
				s20_40MHz(3),
				s20_40_80MHz(4),
				s160MHz(5)
				}
			MAX-ACCESS read-write
			STATUS current
			DESCRIPTION
				"Description."
			::= { priPWifiSwitch 9 }

		
--  1.3.6.1.4.1.37950.1.1.6.2.1.8.5.10
		-- 1.3.6.1.4.1.37950.1.1.6.2.1.8.5.10
		priPWifiEasyMeshStatus OBJECT-TYPE
			SYNTAX INTEGER
				{
				disable(0),
				enable(1)
				}
			MAX-ACCESS read-write
			STATUS current
			DESCRIPTION
				"Description."
			::= { priPWifiSwitch 10 }

		
--  1.3.6.1.4.1.37950.1.1.6.2.1.8.6
		-- 1.3.6.1.4.1.37950.1.1.6.2.1.8.6
		priPWifiSsid OBJECT IDENTIFIER ::= { v1600gPriProfileCfg 6 }

		
--  1.3.6.1.4.1.37950.1.1.6.2.1.8.6.1
		-- 1.3.6.1.4.1.37950.1.1.6.2.1.8.6.1
		priPSsidProfileID OBJECT-TYPE
			SYNTAX Integer32
			MAX-ACCESS read-write
			STATUS current
			DESCRIPTION
				"Description."
			::= { priPWifiSsid 1 }

		
--  1.3.6.1.4.1.37950.1.1.6.2.1.8.6.2
		-- 1.3.6.1.4.1.37950.1.1.6.2.1.8.6.2
		priPSsidId OBJECT-TYPE
			SYNTAX INTEGER (1..10)
			MAX-ACCESS read-write
			STATUS current
			DESCRIPTION
				"Description."
			::= { priPWifiSsid 2 }

		
--  1.3.6.1.4.1.37950.1.1.6.2.1.8.6.3
		-- 1.3.6.1.4.1.37950.1.1.6.2.1.8.6.3
		priPSsidName OBJECT-TYPE
			SYNTAX OCTET STRING
			MAX-ACCESS read-write
			STATUS current
			DESCRIPTION
				"Description."
			::= { priPWifiSsid 3 }

		
--  1.3.6.1.4.1.37950.1.1.6.2.1.8.6.4
		-- 1.3.6.1.4.1.37950.1.1.6.2.1.8.6.4
		priPSsidEnable OBJECT-TYPE
			SYNTAX INTEGER
				{
				disable(0),
				enable(1)
				}
			MAX-ACCESS read-write
			STATUS current
			DESCRIPTION
				"Description."
			::= { priPWifiSsid 4 }

		
--  1.3.6.1.4.1.37950.1.1.6.2.1.8.6.5
		-- 1.3.6.1.4.1.37950.1.1.6.2.1.8.6.5
		priPSsidHide OBJECT-TYPE
			SYNTAX INTEGER
				{
				disable(0),
				enable(1)
				}
			MAX-ACCESS read-write
			STATUS current
			DESCRIPTION
				"Description."
			::= { priPWifiSsid 5 }

		
--  1.3.6.1.4.1.37950.1.1.6.2.1.8.6.6
		-- 1.3.6.1.4.1.37950.1.1.6.2.1.8.6.6
		priPSsidAuthMode OBJECT-TYPE
			SYNTAX INTEGER
				{
				open(1),
				shared(2),
				wepauto(3),
				wpapsk(4),
				wpa(5),
				wpa2psk(6),
				wpa2(7),
				wpa_wpa2(8),
				wpapsk_wpa2psk(9),
				wpa3psk(10),
				wpa2psk_wpa3psk(11)
				}
			MAX-ACCESS read-write
			STATUS current
			DESCRIPTION
				"Description."
			::= { priPWifiSsid 6 }

		
--  1.3.6.1.4.1.37950.1.1.6.2.1.8.6.7
		-- 1.3.6.1.4.1.37950.1.1.6.2.1.8.6.7
		priPSsidEncrypTpye OBJECT-TYPE
			SYNTAX INTEGER
				{
				none(0),
				wep(1),
				tkip(2),
				aes(3),
				tkipaes(4)
				}
			MAX-ACCESS read-write
			STATUS current
			DESCRIPTION
				"Description."
			::= { priPWifiSsid 7 }

		
--  1.3.6.1.4.1.37950.1.1.6.2.1.8.6.8
		-- 1.3.6.1.4.1.37950.1.1.6.2.1.8.6.8
		priPSsidPresharedKey OBJECT-TYPE
			SYNTAX OCTET STRING
			MAX-ACCESS read-write
			STATUS current
			DESCRIPTION
				"Description."
			::= { priPWifiSsid 8 }

		
--  1.3.6.1.4.1.37950.1.1.6.2.1.8.6.9
		-- 1.3.6.1.4.1.37950.1.1.6.2.1.8.6.9
		priPSsidPrekeyInterval OBJECT-TYPE
			SYNTAX INTEGER (0..4194303)
			MAX-ACCESS read-write
			STATUS current
			DESCRIPTION
				"Description."
			::= { priPWifiSsid 9 }

		
--  1.3.6.1.4.1.37950.1.1.6.2.1.8.6.10
		-- 1.3.6.1.4.1.37950.1.1.6.2.1.8.6.10
		priPSsidRadiusSeripType OBJECT-TYPE
			SYNTAX INTEGER
				{
				ipv4(1),
				ipv6(2),
				ipv4z(3),
				ipv6z(4),
				dns(16)
				}
			MAX-ACCESS read-write
			STATUS current
			DESCRIPTION
				"Description."
			::= { priPWifiSsid 10 }

		
--  1.3.6.1.4.1.37950.1.1.6.2.1.8.6.11
		-- 1.3.6.1.4.1.37950.1.1.6.2.1.8.6.11
		priPSsidRadiusSerip OBJECT-TYPE
			SYNTAX OCTET STRING
			MAX-ACCESS read-write
			STATUS current
			DESCRIPTION
				"Description."
			::= { priPWifiSsid 11 }

		
--  1.3.6.1.4.1.37950.1.1.6.2.1.8.6.12
		-- 1.3.6.1.4.1.37950.1.1.6.2.1.8.6.12
		priPSsidRadiusServipPrefixLen OBJECT-TYPE
			SYNTAX INTEGER (0..255)
			MAX-ACCESS read-write
			STATUS current
			DESCRIPTION
				"Description."
			::= { priPWifiSsid 12 }

		
--  1.3.6.1.4.1.37950.1.1.6.2.1.8.6.13
		-- 1.3.6.1.4.1.37950.1.1.6.2.1.8.6.13
		priPSsidRadiusPort OBJECT-TYPE
			SYNTAX INTEGER (0..65535)
			MAX-ACCESS read-write
			STATUS current
			DESCRIPTION
				"Description."
			::= { priPWifiSsid 13 }

		
--  1.3.6.1.4.1.37950.1.1.6.2.1.8.6.14
		-- 1.3.6.1.4.1.37950.1.1.6.2.1.8.6.14
		priPSsidRadiusKey OBJECT-TYPE
			SYNTAX OCTET STRING
			MAX-ACCESS read-write
			STATUS current
			DESCRIPTION
				"Description."
			::= { priPWifiSsid 14 }

		
--  1.3.6.1.4.1.37950.1.1.6.2.1.8.6.15
		-- 1.3.6.1.4.1.37950.1.1.6.2.1.8.6.15
		priPSsidWepEncrytionLevel OBJECT-TYPE
			SYNTAX INTEGER
				{
				s64bit(1),
				s128bit(2)
				}
			MAX-ACCESS read-write
			STATUS current
			DESCRIPTION
				"Description."
			::= { priPWifiSsid 15 }

		
--  1.3.6.1.4.1.37950.1.1.6.2.1.8.6.16
		-- 1.3.6.1.4.1.37950.1.1.6.2.1.8.6.16
		priPSsidWepKeyIndex OBJECT-TYPE
			SYNTAX INTEGER (1..4)
			MAX-ACCESS read-write
			STATUS current
			DESCRIPTION
				"Description."
			::= { priPWifiSsid 16 }

		
--  1.3.6.1.4.1.37950.1.1.6.2.1.8.6.17
		-- 1.3.6.1.4.1.37950.1.1.6.2.1.8.6.17
		priPSsidWepKey1 OBJECT-TYPE
			SYNTAX OCTET STRING
			MAX-ACCESS read-write
			STATUS current
			DESCRIPTION
				"Description."
			::= { priPWifiSsid 17 }

		
--  1.3.6.1.4.1.37950.1.1.6.2.1.8.6.18
		-- 1.3.6.1.4.1.37950.1.1.6.2.1.8.6.18
		priPSsidWepKey2 OBJECT-TYPE
			SYNTAX OCTET STRING
			MAX-ACCESS read-write
			STATUS current
			DESCRIPTION
				"Description."
			::= { priPWifiSsid 18 }

		
--  1.3.6.1.4.1.37950.1.1.6.2.1.8.6.19
		-- 1.3.6.1.4.1.37950.1.1.6.2.1.8.6.19
		priPSsidWepKey3 OBJECT-TYPE
			SYNTAX OCTET STRING
			MAX-ACCESS read-write
			STATUS current
			DESCRIPTION
				"Description."
			::= { priPWifiSsid 19 }

		
--  1.3.6.1.4.1.37950.1.1.6.2.1.8.6.20
		-- 1.3.6.1.4.1.37950.1.1.6.2.1.8.6.20
		priPSsidWepKey4 OBJECT-TYPE
			SYNTAX OCTET STRING
			MAX-ACCESS read-write
			STATUS current
			DESCRIPTION
				"Description."
			::= { priPWifiSsid 20 }

		
--  1.3.6.1.4.1.37950.1.1.6.2.1.8.6.21
		-- 1.3.6.1.4.1.37950.1.1.6.2.1.8.6.21
		priPSsidAction OBJECT-TYPE
			SYNTAX INTEGER
				{
				commit(1),
				remove(2)
				}
			MAX-ACCESS read-write
			STATUS current
			DESCRIPTION
				"Description."
			::= { priPWifiSsid 21 }

		
--  1.3.6.1.4.1.37950.1.1.6.2.1.8.7
		-- 1.3.6.1.4.1.37950.1.1.6.2.1.8.7
		priPSipParam OBJECT IDENTIFIER ::= { v1600gPriProfileCfg 7 }

		
--  1.3.6.1.4.1.37950.1.1.6.2.1.8.7.1
		-- 1.3.6.1.4.1.37950.1.1.6.2.1.8.7.1
		priPSipParamProfileID OBJECT-TYPE
			SYNTAX Integer32
			MAX-ACCESS read-write
			STATUS current
			DESCRIPTION
				"Description."
			::= { priPSipParam 1 }

		
--  1.3.6.1.4.1.37950.1.1.6.2.1.8.7.2
		-- 1.3.6.1.4.1.37950.1.1.6.2.1.8.7.2
		priPProxyServIp OBJECT-TYPE
			SYNTAX OCTET STRING
			MAX-ACCESS read-write
			STATUS current
			DESCRIPTION
				"Description."
			::= { priPSipParam 2 }

		
--  1.3.6.1.4.1.37950.1.1.6.2.1.8.7.3
		-- 1.3.6.1.4.1.37950.1.1.6.2.1.8.7.3
		priPProxyServPort OBJECT-TYPE
			SYNTAX Integer32 (0..65535)
			MAX-ACCESS read-write
			STATUS current
			DESCRIPTION
				"Description."
			::= { priPSipParam 3 }

		
--  1.3.6.1.4.1.37950.1.1.6.2.1.8.7.4
		-- 1.3.6.1.4.1.37950.1.1.6.2.1.8.7.4
		priPBakProxyServIp OBJECT-TYPE
			SYNTAX OCTET STRING
			MAX-ACCESS read-write
			STATUS current
			DESCRIPTION
				"Description."
			::= { priPSipParam 4 }

		
--  1.3.6.1.4.1.37950.1.1.6.2.1.8.7.5
		-- 1.3.6.1.4.1.37950.1.1.6.2.1.8.7.5
		priPBakProxyServPort OBJECT-TYPE
			SYNTAX Integer32 (0..65535)
			MAX-ACCESS read-write
			STATUS current
			DESCRIPTION
				"Description."
			::= { priPSipParam 5 }

		
--  1.3.6.1.4.1.37950.1.1.6.2.1.8.7.6
		-- 1.3.6.1.4.1.37950.1.1.6.2.1.8.7.6
		priPRegServIp OBJECT-TYPE
			SYNTAX OCTET STRING
			MAX-ACCESS read-write
			STATUS current
			DESCRIPTION
				"Description."
			::= { priPSipParam 6 }

		
--  1.3.6.1.4.1.37950.1.1.6.2.1.8.7.7
		-- 1.3.6.1.4.1.37950.1.1.6.2.1.8.7.7
		priPRegServPort OBJECT-TYPE
			SYNTAX Integer32 (0..65535)
			MAX-ACCESS read-write
			STATUS current
			DESCRIPTION
				"Description."
			::= { priPSipParam 7 }

		
--  1.3.6.1.4.1.37950.1.1.6.2.1.8.7.8
		-- 1.3.6.1.4.1.37950.1.1.6.2.1.8.7.8
		priPBakRegServIp OBJECT-TYPE
			SYNTAX OCTET STRING
			MAX-ACCESS read-write
			STATUS current
			DESCRIPTION
				"Description."
			::= { priPSipParam 8 }

		
--  1.3.6.1.4.1.37950.1.1.6.2.1.8.7.9
		-- 1.3.6.1.4.1.37950.1.1.6.2.1.8.7.9
		priPBakRegServPort OBJECT-TYPE
			SYNTAX Integer32 (0..65535)
			MAX-ACCESS read-write
			STATUS current
			DESCRIPTION
				"Description."
			::= { priPSipParam 9 }

		
--  1.3.6.1.4.1.37950.1.1.6.2.1.8.7.10
		-- 1.3.6.1.4.1.37950.1.1.6.2.1.8.7.10
		priPOutBndServIp OBJECT-TYPE
			SYNTAX OCTET STRING
			MAX-ACCESS read-write
			STATUS current
			DESCRIPTION
				"Description."
			::= { priPSipParam 10 }

		
--  1.3.6.1.4.1.37950.1.1.6.2.1.8.7.11
		-- 1.3.6.1.4.1.37950.1.1.6.2.1.8.7.11
		priPOutBndServPort OBJECT-TYPE
			SYNTAX Integer32 (0..65535)
			MAX-ACCESS read-write
			STATUS current
			DESCRIPTION
				"Description."
			::= { priPSipParam 11 }

		
--  1.3.6.1.4.1.37950.1.1.6.2.1.8.7.12
		-- 1.3.6.1.4.1.37950.1.1.6.2.1.8.7.12
		priPSipParamMgPort OBJECT-TYPE
			SYNTAX Integer32 (0..65535)
			MAX-ACCESS read-write
			STATUS current
			DESCRIPTION
				"Description."
			::= { priPSipParam 12 }

		
--  1.3.6.1.4.1.37950.1.1.6.2.1.8.7.13
		-- 1.3.6.1.4.1.37950.1.1.6.2.1.8.7.13
		priPRegInterval OBJECT-TYPE
			SYNTAX Integer32 (0..10000000)
			MAX-ACCESS read-write
			STATUS current
			DESCRIPTION
				"Description."
			::= { priPSipParam 13 }

		
--  1.3.6.1.4.1.37950.1.1.6.2.1.8.7.14
		-- 1.3.6.1.4.1.37950.1.1.6.2.1.8.7.14
		priPSipGloParamAction OBJECT-TYPE
			SYNTAX INTEGER { commit(1) }
			MAX-ACCESS read-write
			STATUS current
			DESCRIPTION
				"Description."
			::= { priPSipParam 14 }

		
--  1.3.6.1.4.1.37950.1.1.6.2.1.8.8
		-- 1.3.6.1.4.1.37950.1.1.6.2.1.8.8
		priPSipDigitMap OBJECT IDENTIFIER ::= { v1600gPriProfileCfg 8 }

		
--  1.3.6.1.4.1.37950.1.1.6.2.1.8.8.1
		-- 1.3.6.1.4.1.37950.1.1.6.2.1.8.8.1
		priPSipDigitMapProfileID OBJECT-TYPE
			SYNTAX Integer32
			MAX-ACCESS read-write
			STATUS current
			DESCRIPTION
				"Description."
			::= { priPSipDigitMap 1 }

		
--  1.3.6.1.4.1.37950.1.1.6.2.1.8.8.2
		-- 1.3.6.1.4.1.37950.1.1.6.2.1.8.8.2
		priPSipDigitMapBlock OBJECT-TYPE
			SYNTAX OCTET STRING
			MAX-ACCESS read-write
			STATUS current
			DESCRIPTION
				"Description."
			::= { priPSipDigitMap 2 }

		
--  1.3.6.1.4.1.37950.1.1.6.2.1.8.8.3
		-- 1.3.6.1.4.1.37950.1.1.6.2.1.8.8.3
		priPSipDigitMapAction OBJECT-TYPE
			SYNTAX INTEGER { commit(1) }
			MAX-ACCESS read-write
			STATUS current
			DESCRIPTION
				"Description."
			::= { priPSipDigitMap 3 }

		
--  1.3.6.1.4.1.37950.1.1.6.2.1.8.9
		-- 1.3.6.1.4.1.37950.1.1.6.2.1.8.9
		priPSipUserParam OBJECT IDENTIFIER ::= { v1600gPriProfileCfg 9 }

		
--  1.3.6.1.4.1.37950.1.1.6.2.1.8.9.1
		-- 1.3.6.1.4.1.37950.1.1.6.2.1.8.9.1
		priPsipUserProfileID OBJECT-TYPE
			SYNTAX Integer32
			MAX-ACCESS read-write
			STATUS current
			DESCRIPTION
				"Description."
			::= { priPSipUserParam 1 }

		
--  1.3.6.1.4.1.37950.1.1.6.2.1.8.9.2
		-- 1.3.6.1.4.1.37950.1.1.6.2.1.8.9.2
		priPsipUserPotsNo OBJECT-TYPE
			SYNTAX Integer32 (1..255)
			MAX-ACCESS read-write
			STATUS current
			DESCRIPTION
				"Description."
			::= { priPSipUserParam 2 }

		
--  1.3.6.1.4.1.37950.1.1.6.2.1.8.9.3
		-- 1.3.6.1.4.1.37950.1.1.6.2.1.8.9.3
		priPsipUserAccountAcitve OBJECT-TYPE
			SYNTAX INTEGER
				{
				disable(0),
				enable(1)
				}
			MAX-ACCESS read-write
			STATUS current
			DESCRIPTION
				"Description."
			::= { priPSipUserParam 3 }

		
--  1.3.6.1.4.1.37950.1.1.6.2.1.8.9.4
		-- 1.3.6.1.4.1.37950.1.1.6.2.1.8.9.4
		priPsipUserAccount OBJECT-TYPE
			SYNTAX OCTET STRING
			MAX-ACCESS read-write
			STATUS current
			DESCRIPTION
				"Description."
			::= { priPSipUserParam 4 }

		
--  1.3.6.1.4.1.37950.1.1.6.2.1.8.9.5
		-- 1.3.6.1.4.1.37950.1.1.6.2.1.8.9.5
		priPsipUserName OBJECT-TYPE
			SYNTAX OCTET STRING
			MAX-ACCESS read-write
			STATUS current
			DESCRIPTION
				"Description."
			::= { priPSipUserParam 5 }

		
--  1.3.6.1.4.1.37950.1.1.6.2.1.8.9.6
		-- 1.3.6.1.4.1.37950.1.1.6.2.1.8.9.6
		priPsipUserPw OBJECT-TYPE
			SYNTAX OCTET STRING
			MAX-ACCESS read-write
			STATUS current
			DESCRIPTION
				"Description."
			::= { priPSipUserParam 6 }

		
--  1.3.6.1.4.1.37950.1.1.6.2.1.8.9.7
		-- 1.3.6.1.4.1.37950.1.1.6.2.1.8.9.7
		priPsipUserAction OBJECT-TYPE
			SYNTAX INTEGER { commit(1) }
			MAX-ACCESS read-write
			STATUS current
			DESCRIPTION
				"Description."
			::= { priPSipUserParam 7 }

		
--  1.3.6.1.4.1.37950.1.1.6.2.1.8.10
		-- 1.3.6.1.4.1.37950.1.1.6.2.1.8.10
		priPPotsParam OBJECT IDENTIFIER ::= { v1600gPriProfileCfg 10 }

		
--  1.3.6.1.4.1.37950.1.1.6.2.1.8.10.1
		-- 1.3.6.1.4.1.37950.1.1.6.2.1.8.10.1
		priPPotsParameterPrpfileID OBJECT-TYPE
			SYNTAX Integer32
			MAX-ACCESS read-write
			STATUS current
			DESCRIPTION
				"Description."
			::= { priPPotsParam 1 }

		
--  1.3.6.1.4.1.37950.1.1.6.2.1.8.10.2
		-- 1.3.6.1.4.1.37950.1.1.6.2.1.8.10.2
		priPPotsParameterPotsNo OBJECT-TYPE
			SYNTAX Integer32 (1..255)
			MAX-ACCESS read-write
			STATUS current
			DESCRIPTION
				"Description."
			::= { priPPotsParam 2 }

		
--  1.3.6.1.4.1.37950.1.1.6.2.1.8.10.3
		-- 1.3.6.1.4.1.37950.1.1.6.2.1.8.10.3
		priPPotsParameterVar OBJECT-TYPE
			SYNTAX INTEGER
				{
				disable(0),
				enable(1)
				}
			MAX-ACCESS read-write
			STATUS current
			DESCRIPTION
				"Description."
			::= { priPPotsParam 3 }

		
--  1.3.6.1.4.1.37950.1.1.6.2.1.8.10.4
		-- 1.3.6.1.4.1.37950.1.1.6.2.1.8.10.4
		priPPotsParameterEchoCancle OBJECT-TYPE
			SYNTAX INTEGER
				{
				disable(0),
				enable(1)
				}
			MAX-ACCESS read-write
			STATUS current
			DESCRIPTION
				"Description."
			::= { priPPotsParam 4 }

		
--  1.3.6.1.4.1.37950.1.1.6.2.1.8.10.5
		-- 1.3.6.1.4.1.37950.1.1.6.2.1.8.10.5
		priPPotsPtInutGain OBJECT-TYPE
			SYNTAX Integer32 (-32..32)
			MAX-ACCESS read-write
			STATUS current
			DESCRIPTION
				"Description."
			::= { priPPotsParam 5 }

		
--  1.3.6.1.4.1.37950.1.1.6.2.1.8.10.6
		-- 1.3.6.1.4.1.37950.1.1.6.2.1.8.10.6
		priPPotsPtOutputGain OBJECT-TYPE
			SYNTAX Integer32 (-32..32)
			MAX-ACCESS read-write
			STATUS current
			DESCRIPTION
				"Description."
			::= { priPPotsParam 6 }

		
--  1.3.6.1.4.1.37950.1.1.6.2.1.8.10.7
		-- 1.3.6.1.4.1.37950.1.1.6.2.1.8.10.7
		priPPotsPtDtmfMode OBJECT-TYPE
			SYNTAX INTEGER
				{
				transparent(0),
				rfc2833(1),
				rfc2833_redundancyl(2),
				outband(3)
				}
			MAX-ACCESS read-write
			STATUS current
			DESCRIPTION
				"Description."
			::= { priPPotsParam 7 }

		
--  1.3.6.1.4.1.37950.1.1.6.2.1.8.10.8
		-- 1.3.6.1.4.1.37950.1.1.6.2.1.8.10.8
		priPPotsPtAction OBJECT-TYPE
			SYNTAX INTEGER
				{
				commit(1),
				remove(2)
				}
			MAX-ACCESS read-write
			STATUS current
			DESCRIPTION
				"Description."
			::= { priPPotsParam 8 }

		
--  1.3.6.1.4.1.37950.1.1.6.2.1.8.11
		-- 1.3.6.1.4.1.37950.1.1.6.2.1.8.11
		priPMiscCtrlOp OBJECT IDENTIFIER ::= { v1600gPriProfileCfg 11 }

		
--  1.3.6.1.4.1.37950.1.1.6.2.1.8.11.1
		-- 1.3.6.1.4.1.37950.1.1.6.2.1.8.11.1
		priPMiscCtrlOpProfileID OBJECT-TYPE
			SYNTAX Integer32
			MAX-ACCESS read-write
			STATUS current
			DESCRIPTION
				"Description."
			::= { priPMiscCtrlOp 1 }

		
--  1.3.6.1.4.1.37950.1.1.6.2.1.8.11.2
		-- 1.3.6.1.4.1.37950.1.1.6.2.1.8.11.2
		priPMiscCtrlOpCatvEnable OBJECT-TYPE
			SYNTAX INTEGER
				{
				disable(0),
				enable(1)
				}
			MAX-ACCESS read-write
			STATUS current
			DESCRIPTION
				"Description."
			::= { priPMiscCtrlOp 2 }

		
--  1.3.6.1.4.1.37950.1.1.6.2.1.8.11.3
		-- 1.3.6.1.4.1.37950.1.1.6.2.1.8.11.3
		priPMiscCtrlOpIgmpEnable OBJECT-TYPE
			SYNTAX INTEGER
				{
				disable(0),
				enable(1)
				}
			MAX-ACCESS read-write
			STATUS current
			DESCRIPTION
				"Description."
			::= { priPMiscCtrlOp 3 }

		
--  1.3.6.1.4.1.37950.1.1.6.2.1.8.11.4
		-- 1.3.6.1.4.1.37950.1.1.6.2.1.8.11.4
		priPMiscCtrlOpStpEnable OBJECT-TYPE
			SYNTAX INTEGER
				{
				disable(0),
				enable(1)
				}
			MAX-ACCESS read-write
			STATUS current
			DESCRIPTION
				"Description."
			::= { priPMiscCtrlOp 4 }

		
--  1.3.6.1.4.1.37950.1.1.6.2.1.8.11.5
		-- 1.3.6.1.4.1.37950.1.1.6.2.1.8.11.5
		priPMiscCtrlOpPortIsoEnable OBJECT-TYPE
			SYNTAX INTEGER
				{
				disable(0),
				enable(1)
				}
			MAX-ACCESS read-write
			STATUS current
			DESCRIPTION
				"Description."
			::= { priPMiscCtrlOp 5 }

		
--  1.3.6.1.4.1.37950.1.1.6.2.1.8.11.6
		-- 1.3.6.1.4.1.37950.1.1.6.2.1.8.11.6
		priPMiscCtrlOpResetButton OBJECT-TYPE
			SYNTAX INTEGER
				{
				disable(0),
				enable(1)
				}
			MAX-ACCESS read-write
			STATUS current
			DESCRIPTION
				"Description."
			::= { priPMiscCtrlOp 6 }

		
--  1.3.6.1.4.1.37950.1.1.6.2.1.8.12
		-- 1.3.6.1.4.1.37950.1.1.6.2.1.8.12
		priPSpeedLimit OBJECT IDENTIFIER ::= { v1600gPriProfileCfg 12 }

		
--  1.3.6.1.4.1.37950.1.1.6.2.1.8.12.1
		-- 1.3.6.1.4.1.37950.1.1.6.2.1.8.12.1
		priPSpeedLimitProfileID OBJECT-TYPE
			SYNTAX Integer32
			MAX-ACCESS read-write
			STATUS current
			DESCRIPTION
				"Description."
			::= { priPSpeedLimit 1 }

		
--  1.3.6.1.4.1.37950.1.1.6.2.1.8.12.2
		-- 1.3.6.1.4.1.37950.1.1.6.2.1.8.12.2
		priPSpeedLimitUpsLimit OBJECT-TYPE
			SYNTAX Integer32
			MAX-ACCESS read-write
			STATUS current
			DESCRIPTION
				"Description."
			::= { priPSpeedLimit 2 }

		
--  1.3.6.1.4.1.37950.1.1.6.2.1.8.12.3
		-- 1.3.6.1.4.1.37950.1.1.6.2.1.8.12.3
		priPSpeedLimitDssLimit OBJECT-TYPE
			SYNTAX Integer32
			MAX-ACCESS read-write
			STATUS current
			DESCRIPTION
				"Description."
			::= { priPSpeedLimit 3 }

		
--  1.3.6.1.4.1.37950.1.1.6.2.1.8.12.4
		-- 1.3.6.1.4.1.37950.1.1.6.2.1.8.12.4
		priPSpeedLimitAction OBJECT-TYPE
			SYNTAX INTEGER { commit(1) }
			MAX-ACCESS read-write
			STATUS current
			DESCRIPTION
				"Description."
			::= { priPSpeedLimit 4 }

		
--  1.3.6.1.4.1.37950.1.1.6.2.1.8.13
		-- 1.3.6.1.4.1.37950.1.1.6.2.1.8.13
		priPMacTableCfg OBJECT IDENTIFIER ::= { v1600gPriProfileCfg 13 }

		
--  1.3.6.1.4.1.37950.1.1.6.2.1.8.13.1
		-- 1.3.6.1.4.1.37950.1.1.6.2.1.8.13.1
		priPMacTableProfileID OBJECT-TYPE
			SYNTAX Integer32
			MAX-ACCESS read-write
			STATUS current
			DESCRIPTION
				"Description."
			::= { priPMacTableCfg 1 }

		
--  1.3.6.1.4.1.37950.1.1.6.2.1.8.13.2
		-- 1.3.6.1.4.1.37950.1.1.6.2.1.8.13.2
		priPMacTableMacAgingTime OBJECT-TYPE
			SYNTAX Integer32
			MAX-ACCESS read-write
			STATUS current
			DESCRIPTION
				"Description."
			::= { priPMacTableCfg 2 }

		
--  1.3.6.1.4.1.37950.1.1.6.2.1.8.13.3
		-- 1.3.6.1.4.1.37950.1.1.6.2.1.8.13.3
		priPMacTablePonMacLimit OBJECT-TYPE
			SYNTAX Integer32
			MAX-ACCESS read-write
			STATUS current
			DESCRIPTION
				"Description."
			::= { priPMacTableCfg 3 }

		
--  1.3.6.1.4.1.37950.1.1.6.2.1.8.13.4
		-- 1.3.6.1.4.1.37950.1.1.6.2.1.8.13.4
		priPMacTableLanMacLimitS OBJECT-TYPE
			SYNTAX Integer32
			MAX-ACCESS read-write
			STATUS current
			DESCRIPTION
				"Description."
			::= { priPMacTableCfg 4 }

		
--  1.3.6.1.4.1.37950.1.1.6.2.1.8.13.5
		-- 1.3.6.1.4.1.37950.1.1.6.2.1.8.13.5
		priPMacTableAction OBJECT-TYPE
			SYNTAX INTEGER { commit(1) }
			MAX-ACCESS read-write
			STATUS current
			DESCRIPTION
				"Description."
			::= { priPMacTableCfg 5 }

		
--  1.3.6.1.4.1.37950.1.1.6.2.1.8.14
		-- 1.3.6.1.4.1.37950.1.1.6.2.1.8.14
		priPUsername OBJECT IDENTIFIER ::= { v1600gPriProfileCfg 14 }

		
--  1.3.6.1.4.1.37950.1.1.6.2.1.8.14.1
		-- 1.3.6.1.4.1.37950.1.1.6.2.1.8.14.1
		priPUsernameProfileID OBJECT-TYPE
			SYNTAX Integer32
			MAX-ACCESS read-write
			STATUS current
			DESCRIPTION
				"Description."
			::= { priPUsername 1 }

		
--  1.3.6.1.4.1.37950.1.1.6.2.1.8.14.2
		-- 1.3.6.1.4.1.37950.1.1.6.2.1.8.14.2
		priPAdminCtl OBJECT-TYPE
			SYNTAX INTEGER
				{
				disable(0),
				enable(1)
				}
			MAX-ACCESS read-write
			STATUS current
			DESCRIPTION
				"Description."
			::= { priPUsername 2 }

		
--  1.3.6.1.4.1.37950.1.1.6.2.1.8.14.3
		-- 1.3.6.1.4.1.37950.1.1.6.2.1.8.14.3
		priPAdminName OBJECT-TYPE
			SYNTAX OCTET STRING
			MAX-ACCESS read-write
			STATUS current
			DESCRIPTION
				"Description."
			::= { priPUsername 3 }

		
--  1.3.6.1.4.1.37950.1.1.6.2.1.8.14.4
		-- 1.3.6.1.4.1.37950.1.1.6.2.1.8.14.4
		priPAdminPwd OBJECT-TYPE
			SYNTAX OCTET STRING
			MAX-ACCESS read-write
			STATUS current
			DESCRIPTION
				"Description."
			::= { priPUsername 4 }

		
--  1.3.6.1.4.1.37950.1.1.6.2.1.8.14.5
		-- 1.3.6.1.4.1.37950.1.1.6.2.1.8.14.5
		priPUserCtl OBJECT-TYPE
			SYNTAX INTEGER
				{
				disable(0),
				enable(1)
				}
			MAX-ACCESS read-write
			STATUS current
			DESCRIPTION
				"Description."
			::= { priPUsername 5 }

		
--  1.3.6.1.4.1.37950.1.1.6.2.1.8.14.6
		-- 1.3.6.1.4.1.37950.1.1.6.2.1.8.14.6
		priPUserName OBJECT-TYPE
			SYNTAX OCTET STRING
			MAX-ACCESS read-write
			STATUS current
			DESCRIPTION
				"Description."
			::= { priPUsername 6 }

		
--  1.3.6.1.4.1.37950.1.1.6.2.1.8.14.7
		-- 1.3.6.1.4.1.37950.1.1.6.2.1.8.14.7
		priPUserPwd OBJECT-TYPE
			SYNTAX OCTET STRING
			MAX-ACCESS read-write
			STATUS current
			DESCRIPTION
				"Description."
			::= { priPUsername 7 }

		
--  1.3.6.1.4.1.37950.1.1.6.2.1.8.14.8
		-- 1.3.6.1.4.1.37950.1.1.6.2.1.8.14.8
		priPUsernameAction OBJECT-TYPE
			SYNTAX INTEGER { add(1) }
			MAX-ACCESS read-write
			STATUS current
			DESCRIPTION
				"Description."
			::= { priPUsername 8 }

		
--  1.3.6.1.4.1.37950.1.1.6.2.1.8.15
		-- 1.3.6.1.4.1.37950.1.1.6.2.1.8.15
		priPriFirewall OBJECT IDENTIFIER ::= { v1600gPriProfileCfg 15 }

		
--  1.3.6.1.4.1.37950.1.1.6.2.1.8.15.1
		-- 1.3.6.1.4.1.37950.1.1.6.2.1.8.15.1
		priPriFirewallProfileID OBJECT-TYPE
			SYNTAX Integer32
			MAX-ACCESS read-write
			STATUS current
			DESCRIPTION
				"Description."
			::= { priPriFirewall 1 }

		
--  1.3.6.1.4.1.37950.1.1.6.2.1.8.15.2
		-- 1.3.6.1.4.1.37950.1.1.6.2.1.8.15.2
		priPFirewall OBJECT-TYPE
			SYNTAX INTEGER
				{
				disable(0),
				low(1),
				middle(2),
				high(3)
				}
			MAX-ACCESS read-write
			STATUS current
			DESCRIPTION
				"Description."
			::= { priPriFirewall 2 }

		
--  1.3.6.1.4.1.37950.1.1.6.2.1.8.16
		-- 1.3.6.1.4.1.37950.1.1.6.2.1.8.16
		priPriAcl OBJECT IDENTIFIER ::= { v1600gPriProfileCfg 16 }

		
--  1.3.6.1.4.1.37950.1.1.6.2.1.8.16.1
		-- 1.3.6.1.4.1.37950.1.1.6.2.1.8.16.1
		priPriAclProfileID OBJECT-TYPE
			SYNTAX Integer32
			MAX-ACCESS read-write
			STATUS current
			DESCRIPTION
				"Description."
			::= { priPriAcl 1 }

		
--  1.3.6.1.4.1.37950.1.1.6.2.1.8.16.2
		-- 1.3.6.1.4.1.37950.1.1.6.2.1.8.16.2
		priPAclProtocol OBJECT-TYPE
			SYNTAX INTEGER
				{
				ping(0),
				telnet(1),
				ftp(2),
				http(3),
				https(4),
				tftp(5),
				ssh(6)
				}
			MAX-ACCESS read-write
			STATUS current
			DESCRIPTION
				"Description."
			::= { priPriAcl 2 }

		
--  1.3.6.1.4.1.37950.1.1.6.2.1.8.16.3
		-- 1.3.6.1.4.1.37950.1.1.6.2.1.8.16.3
		priPAclControl OBJECT-TYPE
			SYNTAX INTEGER
				{
				disable(0),
				enable(1)
				}
			MAX-ACCESS read-write
			STATUS current
			DESCRIPTION
				"Description."
			::= { priPriAcl 3 }

		
--  1.3.6.1.4.1.37950.1.1.6.2.1.8.16.4
		-- 1.3.6.1.4.1.37950.1.1.6.2.1.8.16.4
		priPAclLanControl OBJECT-TYPE
			SYNTAX INTEGER
				{
				disable(0),
				enable(1)
				}
			MAX-ACCESS read-write
			STATUS current
			DESCRIPTION
				"Description."
			::= { priPriAcl 4 }

		
--  1.3.6.1.4.1.37950.1.1.6.2.1.8.16.5
		-- 1.3.6.1.4.1.37950.1.1.6.2.1.8.16.5
		priPAclWanControl OBJECT-TYPE
			SYNTAX INTEGER
				{
				disable(0),
				enable(1)
				}
			MAX-ACCESS read-write
			STATUS current
			DESCRIPTION
				"Description."
			::= { priPriAcl 5 }

		
--  1.3.6.1.4.1.37950.1.1.6.2.1.8.16.6
		-- 1.3.6.1.4.1.37950.1.1.6.2.1.8.16.6
		priPAclaclIPv4Control OBJECT-TYPE
			SYNTAX INTEGER
				{
				disable(0),
				enable(1)
				}
			MAX-ACCESS read-write
			STATUS current
			DESCRIPTION
				"Description."
			::= { priPriAcl 6 }

		
--  1.3.6.1.4.1.37950.1.1.6.2.1.8.16.7
		-- 1.3.6.1.4.1.37950.1.1.6.2.1.8.16.7
		priPAclIPv4Addr OBJECT-TYPE
			SYNTAX IpAddress
			MAX-ACCESS read-write
			STATUS current
			DESCRIPTION
				"Description."
			::= { priPriAcl 7 }

		
--  1.3.6.1.4.1.37950.1.1.6.2.1.8.16.8
		-- 1.3.6.1.4.1.37950.1.1.6.2.1.8.16.8
		priPAclIPv4Mask OBJECT-TYPE
			SYNTAX IpAddress
			MAX-ACCESS read-write
			STATUS current
			DESCRIPTION
				"Description."
			::= { priPriAcl 8 }

		
--  1.3.6.1.4.1.37950.1.1.6.2.1.8.16.9
		-- 1.3.6.1.4.1.37950.1.1.6.2.1.8.16.9
		priPAclIPv6Control OBJECT-TYPE
			SYNTAX INTEGER
				{
				disable(0),
				enable(1)
				}
			MAX-ACCESS read-write
			STATUS current
			DESCRIPTION
				"Description."
			::= { priPriAcl 9 }

		
--  1.3.6.1.4.1.37950.1.1.6.2.1.8.16.10
		-- 1.3.6.1.4.1.37950.1.1.6.2.1.8.16.10
		priPAclIPv6Address OBJECT-TYPE
			SYNTAX OCTET STRING
			MAX-ACCESS read-write
			STATUS current
			DESCRIPTION
				"Description."
			::= { priPriAcl 10 }

		
--  1.3.6.1.4.1.37950.1.1.6.2.1.8.16.11
		-- 1.3.6.1.4.1.37950.1.1.6.2.1.8.16.11
		priPAclIPv6Prefix OBJECT-TYPE
			SYNTAX Unsigned32
			MAX-ACCESS read-write
			STATUS current
			DESCRIPTION
				"Description."
			::= { priPriAcl 11 }

		
--  1.3.6.1.4.1.37950.1.1.6.2.1.8.16.12
		-- 1.3.6.1.4.1.37950.1.1.6.2.1.8.16.12
		priPAclProtocolPort OBJECT-TYPE
			SYNTAX Unsigned32 (0..65535)
			MAX-ACCESS read-write
			STATUS current
			DESCRIPTION
				"Description."
			::= { priPriAcl 12 }

		
--  1.3.6.1.4.1.37950.1.1.6.2.1.8.16.13
		-- 1.3.6.1.4.1.37950.1.1.6.2.1.8.16.13
		priPAclAction OBJECT-TYPE
			SYNTAX INTEGER
				{
				submit(1),
				del(2)
				}
			MAX-ACCESS read-write
			STATUS current
			DESCRIPTION
				"Description."
			::= { priPriAcl 13 }

		
--  1.3.6.1.4.1.37950.1.1.6.2.1.8.17
		-- 1.3.6.1.4.1.37950.1.1.6.2.1.8.17
		priPWanV6 OBJECT IDENTIFIER ::= { v1600gPriProfileCfg 17 }

		
--  1.3.6.1.4.1.37950.1.1.6.2.1.8.17.1
		-- 1.3.6.1.4.1.37950.1.1.6.2.1.8.17.1
		v6WanConnAdd OBJECT IDENTIFIER ::= { priPWanV6 1 }

		
--  1.3.6.1.4.1.37950.1.1.6.2.1.8.17.1.1
		-- 1.3.6.1.4.1.37950.1.1.6.2.1.8.17.1.1
		v6connAddProfileID OBJECT-TYPE
			SYNTAX Integer32
			MAX-ACCESS read-write
			STATUS current
			DESCRIPTION
				"Description."
			::= { v6WanConnAdd 1 }

		
--  1.3.6.1.4.1.37950.1.1.6.2.1.8.17.1.2
		-- 1.3.6.1.4.1.37950.1.1.6.2.1.8.17.1.2
		v6connType OBJECT-TYPE
			SYNTAX INTEGER
				{
				bridge(0),
				route(1)
				}
			MAX-ACCESS read-write
			STATUS current
			DESCRIPTION
				"Description."
			::= { v6WanConnAdd 2 }

		
--  1.3.6.1.4.1.37950.1.1.6.2.1.8.17.1.3
		-- 1.3.6.1.4.1.37950.1.1.6.2.1.8.17.1.3
		v6connAddAction OBJECT-TYPE
			SYNTAX INTEGER { add(1) }
			MAX-ACCESS read-write
			STATUS current
			DESCRIPTION
				"Description."
			::= { v6WanConnAdd 3 }

		
--  1.3.6.1.4.1.37950.1.1.6.2.1.8.17.2
		-- 1.3.6.1.4.1.37950.1.1.6.2.1.8.17.2
		v6WanConnDelete OBJECT IDENTIFIER ::= { priPWanV6 2 }

		
--  1.3.6.1.4.1.37950.1.1.6.2.1.8.17.2.1
		-- 1.3.6.1.4.1.37950.1.1.6.2.1.8.17.2.1
		v6connDeleteProfileID OBJECT-TYPE
			SYNTAX Integer32
			MAX-ACCESS read-write
			STATUS current
			DESCRIPTION
				"Description."
			::= { v6WanConnDelete 1 }

		
--  1.3.6.1.4.1.37950.1.1.6.2.1.8.17.2.2
		-- 1.3.6.1.4.1.37950.1.1.6.2.1.8.17.2.2
		v6connIndexD OBJECT-TYPE
			SYNTAX Integer32 (1..8)
			MAX-ACCESS read-write
			STATUS current
			DESCRIPTION
				"Description."
			::= { v6WanConnDelete 2 }

		
--  1.3.6.1.4.1.37950.1.1.6.2.1.8.17.2.3
		-- 1.3.6.1.4.1.37950.1.1.6.2.1.8.17.2.3
		v6connDeleteAction OBJECT-TYPE
			SYNTAX INTEGER { delete(1) }
			MAX-ACCESS read-write
			STATUS current
			DESCRIPTION
				"Description."
			::= { v6WanConnDelete 3 }

		
--  1.3.6.1.4.1.37950.1.1.6.2.1.8.17.3
		-- 1.3.6.1.4.1.37950.1.1.6.2.1.8.17.3
		v6WanConnCfg OBJECT IDENTIFIER ::= { priPWanV6 3 }

		
--  1.3.6.1.4.1.37950.1.1.6.2.1.8.17.3.1
		-- 1.3.6.1.4.1.37950.1.1.6.2.1.8.17.3.1
		v6ConnCfgProfileID OBJECT-TYPE
			SYNTAX Integer32
			MAX-ACCESS read-write
			STATUS current
			DESCRIPTION
				"Description."
			::= { v6WanConnCfg 1 }

		
--  1.3.6.1.4.1.37950.1.1.6.2.1.8.17.3.2
		-- 1.3.6.1.4.1.37950.1.1.6.2.1.8.17.3.2
		v6ConnIndex OBJECT-TYPE
			SYNTAX INTEGER (1..8)
			MAX-ACCESS read-write
			STATUS current
			DESCRIPTION
				"Description."
			::= { v6WanConnCfg 2 }

		
--  1.3.6.1.4.1.37950.1.1.6.2.1.8.17.3.3
		-- 1.3.6.1.4.1.37950.1.1.6.2.1.8.17.3.3
		v6ConnBindLan OBJECT-TYPE
			SYNTAX INTEGER (0..65535)
			MAX-ACCESS read-write
			STATUS current
			DESCRIPTION
				"Description."
			::= { v6WanConnCfg 3 }

		
--  1.3.6.1.4.1.37950.1.1.6.2.1.8.17.3.4
		-- 1.3.6.1.4.1.37950.1.1.6.2.1.8.17.3.4
		v6ConnBindSsid OBJECT-TYPE
			SYNTAX INTEGER (0..65535)
			MAX-ACCESS read-write
			STATUS current
			DESCRIPTION
				"Description."
			::= { v6WanConnCfg 4 }

		
--  1.3.6.1.4.1.37950.1.1.6.2.1.8.17.3.5
		-- 1.3.6.1.4.1.37950.1.1.6.2.1.8.17.3.5
		v6WanMode OBJECT-TYPE
			SYNTAX INTEGER
				{
				internet(0),
				multicast(1),
				tr069(2),
				tr069_internet(3),
				tr069_voip(4),
				voip_internet(5),
				tr069_voip_internet(6),
				voip(7),
				other(100)
				}
			MAX-ACCESS read-write
			STATUS current
			DESCRIPTION
				"Description."
			::= { v6WanConnCfg 5 }

		
--  1.3.6.1.4.1.37950.1.1.6.2.1.8.17.3.6
		-- 1.3.6.1.4.1.37950.1.1.6.2.1.8.17.3.6
		v6ConnTypeCfg OBJECT-TYPE
			SYNTAX INTEGER
				{
				bridge(0),
				route(1)
				}
			MAX-ACCESS read-write
			STATUS current
			DESCRIPTION
				"Description."
			::= { v6WanConnCfg 6 }

		
--  1.3.6.1.4.1.37950.1.1.6.2.1.8.17.3.7
		-- 1.3.6.1.4.1.37950.1.1.6.2.1.8.17.3.7
		v6ConnVlanId OBJECT-TYPE
			SYNTAX Integer32 (0..4095)
			MAX-ACCESS read-write
			STATUS current
			DESCRIPTION
				"Description."
			::= { v6WanConnCfg 7 }

		
--  1.3.6.1.4.1.37950.1.1.6.2.1.8.17.3.8
		-- 1.3.6.1.4.1.37950.1.1.6.2.1.8.17.3.8
		v6ConnCos OBJECT-TYPE
			SYNTAX INTEGER (0..7)
			MAX-ACCESS read-write
			STATUS current
			DESCRIPTION
				"Description."
			::= { v6WanConnCfg 8 }

		
--  1.3.6.1.4.1.37950.1.1.6.2.1.8.17.3.9
		-- 1.3.6.1.4.1.37950.1.1.6.2.1.8.17.3.9
		v6ConnIpProtocol OBJECT-TYPE
			SYNTAX INTEGER
				{
				ipv4(0),
				ipv6(1),
				ipv4_ipv6(2)
				}
			MAX-ACCESS read-write
			STATUS current
			DESCRIPTION
				"Description."
			::= { v6WanConnCfg 9 }

		
--  1.3.6.1.4.1.37950.1.1.6.2.1.8.17.3.10
		-- 1.3.6.1.4.1.37950.1.1.6.2.1.8.17.3.10
		v6ConnModeCfg OBJECT-TYPE
			SYNTAX INTEGER
				{
				dhcp(0),
				static(1),
				pppoe(2)
				}
			MAX-ACCESS read-write
			STATUS current
			DESCRIPTION
				"Description."
			::= { v6WanConnCfg 10 }

		
--  1.3.6.1.4.1.37950.1.1.6.2.1.8.17.3.11
		-- 1.3.6.1.4.1.37950.1.1.6.2.1.8.17.3.11
		v6ConnIpAddressIpv4 OBJECT-TYPE
			SYNTAX IpAddress
			MAX-ACCESS read-write
			STATUS current
			DESCRIPTION
				"Description."
			::= { v6WanConnCfg 11 }

		
--  1.3.6.1.4.1.37950.1.1.6.2.1.8.17.3.12
		-- 1.3.6.1.4.1.37950.1.1.6.2.1.8.17.3.12
		v6ConnIpNetMaskIpv4 OBJECT-TYPE
			SYNTAX IpAddress
			MAX-ACCESS read-write
			STATUS current
			DESCRIPTION
				"Description."
			::= { v6WanConnCfg 12 }

		
--  1.3.6.1.4.1.37950.1.1.6.2.1.8.17.3.13
		-- 1.3.6.1.4.1.37950.1.1.6.2.1.8.17.3.13
		v6ConnGatewayIpv4 OBJECT-TYPE
			SYNTAX IpAddress
			MAX-ACCESS read-write
			STATUS current
			DESCRIPTION
				"Description."
			::= { v6WanConnCfg 13 }

		
--  1.3.6.1.4.1.37950.1.1.6.2.1.8.17.3.14
		-- 1.3.6.1.4.1.37950.1.1.6.2.1.8.17.3.14
		v6ConnDnsEnableIpv4 OBJECT-TYPE
			SYNTAX INTEGER
				{
				disable(0),
				enable(1)
				}
			MAX-ACCESS read-write
			STATUS current
			DESCRIPTION
				"Description."
			::= { v6WanConnCfg 14 }

		
--  1.3.6.1.4.1.37950.1.1.6.2.1.8.17.3.15
		-- 1.3.6.1.4.1.37950.1.1.6.2.1.8.17.3.15
		v6ConnMasterDnsIpv4 OBJECT-TYPE
			SYNTAX IpAddress
			MAX-ACCESS read-write
			STATUS current
			DESCRIPTION
				"Description."
			::= { v6WanConnCfg 15 }

		
--  1.3.6.1.4.1.37950.1.1.6.2.1.8.17.3.16
		-- 1.3.6.1.4.1.37950.1.1.6.2.1.8.17.3.16
		v6ConnSlaveDnsIpv4 OBJECT-TYPE
			SYNTAX IpAddress
			MAX-ACCESS read-write
			STATUS current
			DESCRIPTION
				"Description."
			::= { v6WanConnCfg 16 }

		
--  1.3.6.1.4.1.37950.1.1.6.2.1.8.17.3.17
		-- 1.3.6.1.4.1.37950.1.1.6.2.1.8.17.3.17
		v6ConnNatEnable OBJECT-TYPE
			SYNTAX INTEGER
				{
				disable(0),
				enable(1)
				}
			MAX-ACCESS read-write
			STATUS current
			DESCRIPTION
				"Description."
			::= { v6WanConnCfg 17 }

		
--  1.3.6.1.4.1.37950.1.1.6.2.1.8.17.3.18
		-- 1.3.6.1.4.1.37950.1.1.6.2.1.8.17.3.18
		v6ConnAddressIpv6 OBJECT-TYPE
			SYNTAX OCTET STRING
			MAX-ACCESS read-write
			STATUS current
			DESCRIPTION
				"Description."
			::= { v6WanConnCfg 18 }

		
--  1.3.6.1.4.1.37950.1.1.6.2.1.8.17.3.19
		-- 1.3.6.1.4.1.37950.1.1.6.2.1.8.17.3.19
		v6ConnPrefixLenIpv6 OBJECT-TYPE
			SYNTAX INTEGER (0..128)
			MAX-ACCESS read-write
			STATUS current
			DESCRIPTION
				"Description."
			::= { v6WanConnCfg 19 }

		
--  1.3.6.1.4.1.37950.1.1.6.2.1.8.17.3.20
		-- 1.3.6.1.4.1.37950.1.1.6.2.1.8.17.3.20
		v6ConnGatewayIpv6 OBJECT-TYPE
			SYNTAX OCTET STRING
			MAX-ACCESS read-write
			STATUS current
			DESCRIPTION
				"Description."
			::= { v6WanConnCfg 20 }

		
--  1.3.6.1.4.1.37950.1.1.6.2.1.8.17.3.21
		-- 1.3.6.1.4.1.37950.1.1.6.2.1.8.17.3.21
		v6ConnDnsEnableIpv6 OBJECT-TYPE
			SYNTAX INTEGER
				{
				disable(0),
				enable(1)
				}
			MAX-ACCESS read-write
			STATUS current
			DESCRIPTION
				"Description."
			::= { v6WanConnCfg 21 }

		
--  1.3.6.1.4.1.37950.1.1.6.2.1.8.17.3.22
		-- 1.3.6.1.4.1.37950.1.1.6.2.1.8.17.3.22
		v6ConnMasterDnsIpv6 OBJECT-TYPE
			SYNTAX OCTET STRING
			MAX-ACCESS read-write
			STATUS current
			DESCRIPTION
				"Description."
			::= { v6WanConnCfg 22 }

		
--  1.3.6.1.4.1.37950.1.1.6.2.1.8.17.3.23
		-- 1.3.6.1.4.1.37950.1.1.6.2.1.8.17.3.23
		v6ConnSlaveDnsIpv6 OBJECT-TYPE
			SYNTAX OCTET STRING
			MAX-ACCESS read-write
			STATUS current
			DESCRIPTION
				"Description."
			::= { v6WanConnCfg 23 }

		
--  1.3.6.1.4.1.37950.1.1.6.2.1.8.17.3.24
		-- 1.3.6.1.4.1.37950.1.1.6.2.1.8.17.3.24
		v6ConnSlaac OBJECT-TYPE
			SYNTAX INTEGER
				{
				disable(0),
				enable(1)
				}
			MAX-ACCESS read-write
			STATUS current
			DESCRIPTION
				"Description."
			::= { v6WanConnCfg 24 }

		
--  1.3.6.1.4.1.37950.1.1.6.2.1.8.17.3.25
		-- 1.3.6.1.4.1.37950.1.1.6.2.1.8.17.3.25
		v6ConnPppoeProxy OBJECT-TYPE
			SYNTAX INTEGER
				{
				disable(0),
				enable(1)
				}
			MAX-ACCESS read-write
			STATUS current
			DESCRIPTION
				"Description."
			::= { v6WanConnCfg 25 }

		
--  1.3.6.1.4.1.37950.1.1.6.2.1.8.17.3.26
		-- 1.3.6.1.4.1.37950.1.1.6.2.1.8.17.3.26
		v6ConnPppoeUsername OBJECT-TYPE
			SYNTAX OCTET STRING
			MAX-ACCESS read-write
			STATUS current
			DESCRIPTION
				"Description."
			::= { v6WanConnCfg 26 }

		
--  1.3.6.1.4.1.37950.1.1.6.2.1.8.17.3.27
		-- 1.3.6.1.4.1.37950.1.1.6.2.1.8.17.3.27
		v6ConnPppoePassword OBJECT-TYPE
			SYNTAX OCTET STRING
			MAX-ACCESS read-write
			STATUS current
			DESCRIPTION
				"Description."
			::= { v6WanConnCfg 27 }

		
--  1.3.6.1.4.1.37950.1.1.6.2.1.8.17.3.28
		-- 1.3.6.1.4.1.37950.1.1.6.2.1.8.17.3.28
		v6ConnPppoeSerName OBJECT-TYPE
			SYNTAX OCTET STRING
			MAX-ACCESS read-write
			STATUS current
			DESCRIPTION
				"Description."
			::= { v6WanConnCfg 28 }

		
--  1.3.6.1.4.1.37950.1.1.6.2.1.8.17.3.29
		-- 1.3.6.1.4.1.37950.1.1.6.2.1.8.17.3.29
		v6ConnPppoeMode OBJECT-TYPE
			SYNTAX INTEGER
				{
				autoConnect(0),
				flowconnect(1)
				}
			MAX-ACCESS read-write
			STATUS current
			DESCRIPTION
				"Description."
			::= { v6WanConnCfg 29 }

		
--  1.3.6.1.4.1.37950.1.1.6.2.1.8.17.3.30
		-- 1.3.6.1.4.1.37950.1.1.6.2.1.8.17.3.30
		v6ConnDhcpv6ClientAddress OBJECT-TYPE
			SYNTAX INTEGER
				{
				disable(0),
				enable(1)
				}
			MAX-ACCESS read-write
			STATUS current
			DESCRIPTION
				"Description."
			::= { v6WanConnCfg 30 }

		
--  1.3.6.1.4.1.37950.1.1.6.2.1.8.17.3.31
		-- 1.3.6.1.4.1.37950.1.1.6.2.1.8.17.3.31
		v6ConnDhcpv6ClientPrefix OBJECT-TYPE
			SYNTAX INTEGER
				{
				disable(0),
				enable(1)
				}
			MAX-ACCESS read-write
			STATUS current
			DESCRIPTION
				"Description."
			::= { v6WanConnCfg 31 }

		
--  1.3.6.1.4.1.37950.1.1.6.2.1.8.17.3.32
		-- 1.3.6.1.4.1.37950.1.1.6.2.1.8.17.3.32
		v6ConnDsLiteEnable OBJECT-TYPE
			SYNTAX INTEGER
				{
				disable(0),
				enable(1)
				}
			MAX-ACCESS read-write
			STATUS current
			DESCRIPTION
				"Description."
			::= { v6WanConnCfg 32 }

		
--  1.3.6.1.4.1.37950.1.1.6.2.1.8.17.3.33
		-- 1.3.6.1.4.1.37950.1.1.6.2.1.8.17.3.33
		v6ConnDsLiteAftrMode OBJECT-TYPE
			SYNTAX INTEGER
				{
				dhcpv6(0),
				manual(1)
				}
			MAX-ACCESS read-write
			STATUS current
			DESCRIPTION
				"Description."
			::= { v6WanConnCfg 33 }

		
--  1.3.6.1.4.1.37950.1.1.6.2.1.8.17.3.34
		-- 1.3.6.1.4.1.37950.1.1.6.2.1.8.17.3.34
		v6ConnDsLiteAddressType OBJECT-TYPE
			SYNTAX INTEGER
				{
				ipv6(0),
				dns(1)
				}
			MAX-ACCESS read-write
			STATUS current
			DESCRIPTION
				"Description."
			::= { v6WanConnCfg 34 }

		
--  1.3.6.1.4.1.37950.1.1.6.2.1.8.17.3.35
		-- 1.3.6.1.4.1.37950.1.1.6.2.1.8.17.3.35
		v6ConnDsLiteAddress OBJECT-TYPE
			SYNTAX OCTET STRING
			MAX-ACCESS read-write
			STATUS current
			DESCRIPTION
				"Description."
			::= { v6WanConnCfg 35 }

		
--  1.3.6.1.4.1.37950.1.1.6.2.1.8.17.3.36
		-- 1.3.6.1.4.1.37950.1.1.6.2.1.8.17.3.36
		v6ConnQosEnable OBJECT-TYPE
			SYNTAX INTEGER
				{
				disable(0),
				enable(1)
				}
			MAX-ACCESS read-write
			STATUS current
			DESCRIPTION
				"Description."
			::= { v6WanConnCfg 36 }

		
--  1.3.6.1.4.1.37950.1.1.6.2.1.8.17.3.37
		-- 1.3.6.1.4.1.37950.1.1.6.2.1.8.17.3.37
		v6ConnVlanMode OBJECT-TYPE
			SYNTAX INTEGER
				{
				disable(0),
				tag(1),
				transparent(2)
				}
			MAX-ACCESS read-write
			STATUS current
			DESCRIPTION
				"Description."
			::= { v6WanConnCfg 37 }

		
--  1.3.6.1.4.1.37950.1.1.6.2.1.8.17.3.38
		-- 1.3.6.1.4.1.37950.1.1.6.2.1.8.17.3.38
		v6ConnTranslationEnable OBJECT-TYPE
			SYNTAX INTEGER
				{
				disable(0),
				enable(1)
				}
			MAX-ACCESS read-write
			STATUS current
			DESCRIPTION
				"Description."
			::= { v6WanConnCfg 38 }

		
--  1.3.6.1.4.1.37950.1.1.6.2.1.8.17.3.39
		-- 1.3.6.1.4.1.37950.1.1.6.2.1.8.17.3.39
		v6ConnTranslationVlan OBJECT-TYPE
			SYNTAX INTEGER (1..4095)
			MAX-ACCESS read-write
			STATUS current
			DESCRIPTION
				"Description."
			::= { v6WanConnCfg 39 }

		
--  1.3.6.1.4.1.37950.1.1.6.2.1.8.17.3.40
		-- 1.3.6.1.4.1.37950.1.1.6.2.1.8.17.3.40
		v6ConnTranslationCos OBJECT-TYPE
			SYNTAX INTEGER (0..7)
			MAX-ACCESS read-write
			STATUS current
			DESCRIPTION
				"Description."
			::= { v6WanConnCfg 40 }

		
--  1.3.6.1.4.1.37950.1.1.6.2.1.8.17.3.41
		-- 1.3.6.1.4.1.37950.1.1.6.2.1.8.17.3.41
		v6ConnQinqEnable OBJECT-TYPE
			SYNTAX INTEGER
				{
				disable(0),
				enable(1)
				}
			MAX-ACCESS read-write
			STATUS current
			DESCRIPTION
				"Description."
			::= { v6WanConnCfg 41 }

		
--  1.3.6.1.4.1.37950.1.1.6.2.1.8.17.3.42
		-- 1.3.6.1.4.1.37950.1.1.6.2.1.8.17.3.42
		v6ConnQinqTpid OBJECT-TYPE
			SYNTAX Integer32 (1..65534)
			MAX-ACCESS read-write
			STATUS current
			DESCRIPTION
				"Description."
			::= { v6WanConnCfg 42 }

		
--  1.3.6.1.4.1.37950.1.1.6.2.1.8.17.3.43
		-- 1.3.6.1.4.1.37950.1.1.6.2.1.8.17.3.43
		v6ConnWanSvlanId OBJECT-TYPE
			SYNTAX INTEGER (1..4095)
			MAX-ACCESS read-write
			STATUS current
			DESCRIPTION
				"Description."
			::= { v6WanConnCfg 43 }

		
--  1.3.6.1.4.1.37950.1.1.6.2.1.8.17.3.44
		-- 1.3.6.1.4.1.37950.1.1.6.2.1.8.17.3.44
		v6ConnSvlanCos OBJECT-TYPE
			SYNTAX INTEGER (0..7)
			MAX-ACCESS read-write
			STATUS current
			DESCRIPTION
				"Description."
			::= { v6WanConnCfg 44 }

		
--  1.3.6.1.4.1.37950.1.1.6.2.1.8.17.3.45
		-- 1.3.6.1.4.1.37950.1.1.6.2.1.8.17.3.45
		v6ConnRouteMtu OBJECT-TYPE
			SYNTAX Integer32 (0 | 576..1500)
			MAX-ACCESS read-write
			STATUS current
			DESCRIPTION
				"Description."
			::= { v6WanConnCfg 45 }

		
--  1.3.6.1.4.1.37950.1.1.6.2.1.8.17.3.46
		-- 1.3.6.1.4.1.37950.1.1.6.2.1.8.17.3.46
		v6ConnCfgAction OBJECT-TYPE
			SYNTAX INTEGER { commit(1) }
			MAX-ACCESS read-write
			STATUS current
			DESCRIPTION
				"Description."
			::= { v6WanConnCfg 46 }

		
--  1.3.6.1.4.1.37950.1.1.6.2.1.8.18
		-- 1.3.6.1.4.1.37950.1.1.6.2.1.8.18
		priPDhcpServerV6 OBJECT IDENTIFIER ::= { v1600gPriProfileCfg 18 }

		
--  1.3.6.1.4.1.37950.1.1.6.2.1.8.18.1
		-- 1.3.6.1.4.1.37950.1.1.6.2.1.8.18.1
		priPDhcpServerV6ProfileID OBJECT-TYPE
			SYNTAX Integer32
			MAX-ACCESS read-write
			STATUS current
			DESCRIPTION
				"Description."
			::= { priPDhcpServerV6 1 }

		
--  1.3.6.1.4.1.37950.1.1.6.2.1.8.18.2
		-- 1.3.6.1.4.1.37950.1.1.6.2.1.8.18.2
		dhcpv6Lanip OBJECT-TYPE
			SYNTAX OCTET STRING
			MAX-ACCESS read-write
			STATUS current
			DESCRIPTION
				"Description."
			::= { priPDhcpServerV6 2 }

		
--  1.3.6.1.4.1.37950.1.1.6.2.1.8.18.3
		-- 1.3.6.1.4.1.37950.1.1.6.2.1.8.18.3
		dhcpv6lanPrefixlen OBJECT-TYPE
			SYNTAX INTEGER (48..64)
			MAX-ACCESS read-write
			STATUS current
			DESCRIPTION
				"Description."
			::= { priPDhcpServerV6 3 }

		
--  1.3.6.1.4.1.37950.1.1.6.2.1.8.18.4
		-- 1.3.6.1.4.1.37950.1.1.6.2.1.8.18.4
		dhcpv6PrefixMode OBJECT-TYPE
			SYNTAX INTEGER
				{
				wan_delegated(0),
				static(1),
				auto(2)
				}
			MAX-ACCESS read-write
			STATUS current
			DESCRIPTION
				"Description."
			::= { priPDhcpServerV6 4 }

		
--  1.3.6.1.4.1.37950.1.1.6.2.1.8.18.5
		-- 1.3.6.1.4.1.37950.1.1.6.2.1.8.18.5
		dhcpv6PrefixModeIp OBJECT-TYPE
			SYNTAX OCTET STRING
			MAX-ACCESS read-write
			STATUS current
			DESCRIPTION
				"Description."
			::= { priPDhcpServerV6 5 }

		
--  1.3.6.1.4.1.37950.1.1.6.2.1.8.18.6
		-- 1.3.6.1.4.1.37950.1.1.6.2.1.8.18.6
		dhcpv6ServerEnable OBJECT-TYPE
			SYNTAX INTEGER
				{
				disable(0),
				enable(1),
				relay(2)
				}
			MAX-ACCESS read-write
			STATUS current
			DESCRIPTION
				"Description."
			::= { priPDhcpServerV6 6 }

		
--  1.3.6.1.4.1.37950.1.1.6.2.1.8.18.7
		-- 1.3.6.1.4.1.37950.1.1.6.2.1.8.18.7
		dhcpv6Preference OBJECT-TYPE
			SYNTAX Unsigned32 (0..4294967295)
			MAX-ACCESS read-write
			STATUS current
			DESCRIPTION
				"Description."
			::= { priPDhcpServerV6 7 }

		
--  1.3.6.1.4.1.37950.1.1.6.2.1.8.18.8
		-- 1.3.6.1.4.1.37950.1.1.6.2.1.8.18.8
		dhcpv6BeginIp OBJECT-TYPE
			SYNTAX OCTET STRING
			MAX-ACCESS read-write
			STATUS current
			DESCRIPTION
				"Description."
			::= { priPDhcpServerV6 8 }

		
--  1.3.6.1.4.1.37950.1.1.6.2.1.8.18.9
		-- 1.3.6.1.4.1.37950.1.1.6.2.1.8.18.9
		dhcpv6EndIp OBJECT-TYPE
			SYNTAX OCTET STRING
			MAX-ACCESS read-write
			STATUS current
			DESCRIPTION
				"Description."
			::= { priPDhcpServerV6 9 }

		
--  1.3.6.1.4.1.37950.1.1.6.2.1.8.18.10
		-- 1.3.6.1.4.1.37950.1.1.6.2.1.8.18.10
		dhcpv6PoolType OBJECT-TYPE
			SYNTAX INTEGER
				{
				pc(0),
				camera(1),
				stb(2),
				ip_phone(3)
				}
			MAX-ACCESS read-write
			STATUS current
			DESCRIPTION
				"Description."
			::= { priPDhcpServerV6 10 }

		
--  1.3.6.1.4.1.37950.1.1.6.2.1.8.18.11
		-- 1.3.6.1.4.1.37950.1.1.6.2.1.8.18.11
		dhcpv6MasterDns OBJECT-TYPE
			SYNTAX OCTET STRING
			MAX-ACCESS read-write
			STATUS current
			DESCRIPTION
				"Description."
			::= { priPDhcpServerV6 11 }

		
--  1.3.6.1.4.1.37950.1.1.6.2.1.8.18.12
		-- 1.3.6.1.4.1.37950.1.1.6.2.1.8.18.12
		dhcpv6SlaveDns OBJECT-TYPE
			SYNTAX OCTET STRING
			MAX-ACCESS read-write
			STATUS current
			DESCRIPTION
				"Description."
			::= { priPDhcpServerV6 12 }

		
--  1.3.6.1.4.1.37950.1.1.6.2.1.8.18.13
		-- 1.3.6.1.4.1.37950.1.1.6.2.1.8.18.13
		dhcpv6Gateway OBJECT-TYPE
			SYNTAX OCTET STRING
			MAX-ACCESS read-write
			STATUS current
			DESCRIPTION
				"Description."
			::= { priPDhcpServerV6 13 }

		
--  1.3.6.1.4.1.37950.1.1.6.2.1.8.18.14
		-- 1.3.6.1.4.1.37950.1.1.6.2.1.8.18.14
		dhcpv6RelayIp OBJECT-TYPE
			SYNTAX OCTET STRING
			MAX-ACCESS read-write
			STATUS current
			DESCRIPTION
				"Description."
			::= { priPDhcpServerV6 14 }

		
--  1.3.6.1.4.1.37950.1.1.6.2.1.8.18.15
		-- 1.3.6.1.4.1.37950.1.1.6.2.1.8.18.15
		dhcpv6RA OBJECT-TYPE
			SYNTAX INTEGER
				{
				disable(0),
				enable(1)
				}
			MAX-ACCESS read-write
			STATUS current
			DESCRIPTION
				"Description."
			::= { priPDhcpServerV6 15 }

		
--  1.3.6.1.4.1.37950.1.1.6.2.1.8.18.16
		-- 1.3.6.1.4.1.37950.1.1.6.2.1.8.18.16
		dhcpv6RAManage OBJECT-TYPE
			SYNTAX INTEGER
				{
				disable(0),
				enable(1)
				}
			MAX-ACCESS read-write
			STATUS current
			DESCRIPTION
				"Description."
			::= { priPDhcpServerV6 16 }

		
--  1.3.6.1.4.1.37950.1.1.6.2.1.8.18.17
		-- 1.3.6.1.4.1.37950.1.1.6.2.1.8.18.17
		dhcpv6RAOther OBJECT-TYPE
			SYNTAX INTEGER
				{
				disable(0),
				enable(1)
				}
			MAX-ACCESS read-write
			STATUS current
			DESCRIPTION
				"Description."
			::= { priPDhcpServerV6 17 }

		
--  1.3.6.1.4.1.37950.1.1.6.2.1.8.18.18
		-- 1.3.6.1.4.1.37950.1.1.6.2.1.8.18.18
		dhcpv6RAMaxInterval OBJECT-TYPE
			SYNTAX Integer32 (1..1800)
			MAX-ACCESS read-write
			STATUS current
			DESCRIPTION
				"Description."
			::= { priPDhcpServerV6 18 }

		
--  1.3.6.1.4.1.37950.1.1.6.2.1.8.18.19
		-- 1.3.6.1.4.1.37950.1.1.6.2.1.8.18.19
		dhcpv6RAMinInterval OBJECT-TYPE
			SYNTAX Integer32 (1..1800)
			MAX-ACCESS read-write
			STATUS current
			DESCRIPTION
				"Description."
			::= { priPDhcpServerV6 19 }

		
--  1.3.6.1.4.1.37950.1.1.6.2.1.8.18.20
		-- 1.3.6.1.4.1.37950.1.1.6.2.1.8.18.20
		dhcpv6Action OBJECT-TYPE
			SYNTAX INTEGER
				{
				commit(1),
				remove(2)
				}
			MAX-ACCESS read-write
			STATUS current
			DESCRIPTION
				"Description."
			::= { priPDhcpServerV6 20 }

		
--  1.3.6.1.4.1.37950.1.1.6.2.1.8.18.21
		-- 1.3.6.1.4.1.37950.1.1.6.2.1.8.18.21
		dhcpv6Valid OBJECT-TYPE
			SYNTAX Unsigned32 (0..4294967295)
			MAX-ACCESS read-write
			STATUS current
			DESCRIPTION
				"Description."
			::= { priPDhcpServerV6 21 }

		
--  1.3.6.1.4.1.37950.1.1.6.2.1.8.18.22
		-- 1.3.6.1.4.1.37950.1.1.6.2.1.8.18.22
		dhcpv6PrefixModeWanIndex OBJECT-TYPE
			SYNTAX Integer32 (1..8)
			MAX-ACCESS read-write
			STATUS current
			DESCRIPTION
				"Description."
			::= { priPDhcpServerV6 22 }

		
--  1.3.6.1.4.1.37950.1.1.6.2.1.8.18.23
		-- 1.3.6.1.4.1.37950.1.1.6.2.1.8.18.23
		dhcpv6DNSMode OBJECT-TYPE
			SYNTAX INTEGER
				{
				wanconnection(0),
				static(1),
				hgwproxy(2)
				}
			MAX-ACCESS read-write
			STATUS current
			DESCRIPTION
				"Description."
			::= { priPDhcpServerV6 23 }

		
--  1.3.6.1.4.1.37950.1.1.6.2.1.8.18.24
		-- 1.3.6.1.4.1.37950.1.1.6.2.1.8.18.24
		dhcpv6DNSModeWanIndex OBJECT-TYPE
			SYNTAX Integer32 (1..8)
			MAX-ACCESS read-write
			STATUS current
			DESCRIPTION
				"Description."
			::= { priPDhcpServerV6 24 }

		
--  1.3.6.1.4.1.37950.1.1.6.2.1.8.19
		-- 1.3.6.1.4.1.37950.1.1.6.2.1.8.19
		priPLoopChk OBJECT IDENTIFIER ::= { v1600gPriProfileCfg 19 }

		
--  1.3.6.1.4.1.37950.1.1.6.2.1.8.19.1
		-- 1.3.6.1.4.1.37950.1.1.6.2.1.8.19.1
		priPLCProfileID OBJECT-TYPE
			SYNTAX Integer32
			MAX-ACCESS read-write
			STATUS current
			DESCRIPTION
				"Description."
			::= { priPLoopChk 1 }

		
--  1.3.6.1.4.1.37950.1.1.6.2.1.8.19.2
		-- 1.3.6.1.4.1.37950.1.1.6.2.1.8.19.2
		priPLCStatus OBJECT-TYPE
			SYNTAX INTEGER
				{
				disable(0),
				enable(1)
				}
			MAX-ACCESS read-write
			STATUS current
			DESCRIPTION
				"Description."
			::= { priPLoopChk 2 }

		
--  1.3.6.1.4.1.37950.1.1.6.2.1.8.19.3
		-- 1.3.6.1.4.1.37950.1.1.6.2.1.8.19.3
		priPLCCheckInterval OBJECT-TYPE
			SYNTAX Integer32 (1..60000)
			MAX-ACCESS read-write
			STATUS current
			DESCRIPTION
				"Description."
			DEFVAL { 1000 }
			::= { priPLoopChk 3 }

		
--  1.3.6.1.4.1.37950.1.1.6.2.1.8.19.4
		-- 1.3.6.1.4.1.37950.1.1.6.2.1.8.19.4
		priPLCRecoverInterval OBJECT-TYPE
			SYNTAX Integer32 (1..1800)
			MAX-ACCESS read-write
			STATUS current
			DESCRIPTION
				"Description."
			DEFVAL { 60 }
			::= { priPLoopChk 4 }

		
--  1.3.6.1.4.1.37950.1.1.6.2.1.8.19.5
		-- 1.3.6.1.4.1.37950.1.1.6.2.1.8.19.5
		priPLCEthernetType OBJECT-TYPE
			SYNTAX OCTET STRING
			MAX-ACCESS read-write
			STATUS current
			DESCRIPTION
				"Description."
			DEFVAL { "fffa" }
			::= { priPLoopChk 5 }

		
--  1.3.6.1.4.1.37950.1.1.6.2.1.8.19.6
		-- 1.3.6.1.4.1.37950.1.1.6.2.1.8.19.6
		priPLCVlan OBJECT-TYPE
			SYNTAX Integer32 (0..4094)
			MAX-ACCESS read-write
			STATUS current
			DESCRIPTION
				"Description."
			DEFVAL { 0 }
			::= { priPLoopChk 6 }

		
--  1.3.6.1.4.1.37950.1.1.6.2.1.8.19.7
		-- 1.3.6.1.4.1.37950.1.1.6.2.1.8.19.7
		priPLCDestMacType OBJECT-TYPE
			SYNTAX INTEGER
				{
				broadcast_address(0),
				bpdu_address(1)
				}
			MAX-ACCESS read-write
			STATUS current
			DESCRIPTION
				"Description."
			::= { priPLoopChk 7 }

		
--  1.3.6.1.4.1.37950.1.1.6.2.1.8.19.8
		-- 1.3.6.1.4.1.37950.1.1.6.2.1.8.19.8
		priPLCPortClosingTime OBJECT-TYPE
			SYNTAX Integer32 (1..1800)
			MAX-ACCESS read-write
			STATUS current
			DESCRIPTION
				"Description."
			DEFVAL { 60 }
			::= { priPLoopChk 8 }

		
--  1.3.6.1.4.1.37950.1.1.6.2.1.8.19.9
		-- 1.3.6.1.4.1.37950.1.1.6.2.1.8.19.9
		priPLCAlarm OBJECT-TYPE
			SYNTAX INTEGER
				{
				disable(0),
				enable(1)
				}
			MAX-ACCESS read-write
			STATUS current
			DESCRIPTION
				"Description."
			::= { priPLoopChk 9 }

		
--  1.3.6.1.4.1.37950.1.1.6.2.1.8.19.10
		-- 1.3.6.1.4.1.37950.1.1.6.2.1.8.19.10
		priPLCPortdislooped OBJECT-TYPE
			SYNTAX INTEGER
				{
				disable(0),
				enable(1)
				}
			MAX-ACCESS read-write
			STATUS current
			DESCRIPTION
				"Description."
			::= { priPLoopChk 10 }

		
--  1.3.6.1.4.1.37950.1.1.6.2.1.8.19.11
		-- 1.3.6.1.4.1.37950.1.1.6.2.1.8.19.11
		priPLCAction OBJECT-TYPE
			SYNTAX INTEGER { submit(1) }
			MAX-ACCESS read-write
			STATUS current
			DESCRIPTION
				"Description."
			::= { priPLoopChk 11 }

		
--  1.3.6.1.4.1.37950.1.1.6.2.1.8.20
		-- 1.3.6.1.4.1.37950.1.1.6.2.1.8.20
		priPTr069 OBJECT IDENTIFIER ::= { v1600gPriProfileCfg 20 }

		
--  1.3.6.1.4.1.37950.1.1.6.2.1.8.20.1
		-- 1.3.6.1.4.1.37950.1.1.6.2.1.8.20.1
		onuTr069Manage OBJECT IDENTIFIER ::= { priPTr069 1 }

		
--  1.3.6.1.4.1.37950.1.1.6.2.1.8.20.1.1
		-- 1.3.6.1.4.1.37950.1.1.6.2.1.8.20.1.1
		mngPID OBJECT-TYPE
			SYNTAX Integer32
			MAX-ACCESS read-write
			STATUS current
			DESCRIPTION
				"Description."
			::= { onuTr069Manage 1 }

		
--  1.3.6.1.4.1.37950.1.1.6.2.1.8.20.1.2
		-- 1.3.6.1.4.1.37950.1.1.6.2.1.8.20.1.2
		mngStatus OBJECT-TYPE
			SYNTAX INTEGER
				{
				disable(0),
				enable(1)
				}
			MAX-ACCESS read-write
			STATUS current
			DESCRIPTION
				"Description."
			::= { onuTr069Manage 2 }

		
--  1.3.6.1.4.1.37950.1.1.6.2.1.8.20.1.3
		-- 1.3.6.1.4.1.37950.1.1.6.2.1.8.20.1.3
		mngAcsAddress OBJECT-TYPE
			SYNTAX OCTET STRING (SIZE (0..128))
			MAX-ACCESS read-write
			STATUS current
			DESCRIPTION
				"Description."
			::= { onuTr069Manage 3 }

		
--  1.3.6.1.4.1.37950.1.1.6.2.1.8.20.1.4
		-- 1.3.6.1.4.1.37950.1.1.6.2.1.8.20.1.4
		mngAcsUsername OBJECT-TYPE
			SYNTAX OCTET STRING (SIZE (0..64))
			MAX-ACCESS read-write
			STATUS current
			DESCRIPTION
				"Description."
			::= { onuTr069Manage 4 }

		
--  1.3.6.1.4.1.37950.1.1.6.2.1.8.20.1.5
		-- 1.3.6.1.4.1.37950.1.1.6.2.1.8.20.1.5
		mngAcsPassword OBJECT-TYPE
			SYNTAX OCTET STRING (SIZE (0..64))
			MAX-ACCESS read-write
			STATUS current
			DESCRIPTION
				"Description."
			::= { onuTr069Manage 5 }

		
--  1.3.6.1.4.1.37950.1.1.6.2.1.8.20.1.6
		-- 1.3.6.1.4.1.37950.1.1.6.2.1.8.20.1.6
		mngCertificateEn OBJECT-TYPE
			SYNTAX INTEGER
				{
				disable(0),
				enable(1)
				}
			MAX-ACCESS read-write
			STATUS current
			DESCRIPTION
				"Description."
			::= { onuTr069Manage 6 }

		
--  1.3.6.1.4.1.37950.1.1.6.2.1.8.20.1.7
		-- 1.3.6.1.4.1.37950.1.1.6.2.1.8.20.1.7
		mngInformEn OBJECT-TYPE
			SYNTAX INTEGER
				{
				disable(0),
				enable(1)
				}
			MAX-ACCESS read-write
			STATUS current
			DESCRIPTION
				"Description."
			::= { onuTr069Manage 7 }

		
--  1.3.6.1.4.1.37950.1.1.6.2.1.8.20.1.8
		-- 1.3.6.1.4.1.37950.1.1.6.2.1.8.20.1.8
		mngInformIntervalTime OBJECT-TYPE
			SYNTAX Unsigned32 (0..4294967295)
			MAX-ACCESS read-write
			STATUS current
			DESCRIPTION
				"Description."
			::= { onuTr069Manage 8 }

		
--  1.3.6.1.4.1.37950.1.1.6.2.1.8.20.1.9
		-- 1.3.6.1.4.1.37950.1.1.6.2.1.8.20.1.9
		mngRevConnUsername OBJECT-TYPE
			SYNTAX OCTET STRING (SIZE (0..64))
			MAX-ACCESS read-write
			STATUS current
			DESCRIPTION
				"Description."
			::= { onuTr069Manage 9 }

		
--  1.3.6.1.4.1.37950.1.1.6.2.1.8.20.1.10
		-- 1.3.6.1.4.1.37950.1.1.6.2.1.8.20.1.10
		mngRevConnPassword OBJECT-TYPE
			SYNTAX OCTET STRING (SIZE (0..64))
			MAX-ACCESS read-write
			STATUS current
			DESCRIPTION
				"Description."
			::= { onuTr069Manage 10 }

		
--  1.3.6.1.4.1.37950.1.1.6.2.1.8.20.1.11
		-- 1.3.6.1.4.1.37950.1.1.6.2.1.8.20.1.11
		mngAction OBJECT-TYPE
			SYNTAX INTEGER
				{
				submit(1),
				remove(2)
				}
			MAX-ACCESS read-write
			STATUS current
			DESCRIPTION
				"Description."
			::= { onuTr069Manage 11 }

		
--  1.3.6.1.4.1.37950.1.1.6.2.1.8.20.1.12
		-- 1.3.6.1.4.1.37950.1.1.6.2.1.8.20.1.12
		mngID OBJECT-TYPE
			SYNTAX OCTET STRING
			MAX-ACCESS read-write
			STATUS current
			DESCRIPTION
				"Description."
			::= { onuTr069Manage 12 }

		
--  1.3.6.1.4.1.37950.1.1.6.2.1.8.20.2
		-- 1.3.6.1.4.1.37950.1.1.6.2.1.8.20.2
		onuTr069Stun OBJECT IDENTIFIER ::= { priPTr069 2 }

		
--  1.3.6.1.4.1.37950.1.1.6.2.1.8.20.2.1
		-- 1.3.6.1.4.1.37950.1.1.6.2.1.8.20.2.1
		stunPID OBJECT-TYPE
			SYNTAX Integer32
			MAX-ACCESS read-write
			STATUS current
			DESCRIPTION
				"Description."
			::= { onuTr069Stun 1 }

		
--  1.3.6.1.4.1.37950.1.1.6.2.1.8.20.2.2
		-- 1.3.6.1.4.1.37950.1.1.6.2.1.8.20.2.2
		stunStatus OBJECT-TYPE
			SYNTAX INTEGER
				{
				disable(0),
				enable(1)
				}
			MAX-ACCESS read-write
			STATUS current
			DESCRIPTION
				"Description."
			::= { onuTr069Stun 2 }

		
--  1.3.6.1.4.1.37950.1.1.6.2.1.8.20.2.3
		-- 1.3.6.1.4.1.37950.1.1.6.2.1.8.20.2.3
		stunServerAddress OBJECT-TYPE
			SYNTAX OCTET STRING (SIZE (0..128))
			MAX-ACCESS read-write
			STATUS current
			DESCRIPTION
				"Description."
			::= { onuTr069Stun 3 }

		
--  1.3.6.1.4.1.37950.1.1.6.2.1.8.20.2.4
		-- 1.3.6.1.4.1.37950.1.1.6.2.1.8.20.2.4
		stunServerPort OBJECT-TYPE
			SYNTAX Integer32 (1..65535)
			MAX-ACCESS read-write
			STATUS current
			DESCRIPTION
				"Description."
			::= { onuTr069Stun 4 }

		
--  1.3.6.1.4.1.37950.1.1.6.2.1.8.20.2.5
		-- 1.3.6.1.4.1.37950.1.1.6.2.1.8.20.2.5
		stunServerUsername OBJECT-TYPE
			SYNTAX OCTET STRING (SIZE (0..64))
			MAX-ACCESS read-write
			STATUS current
			DESCRIPTION
				"Description."
			::= { onuTr069Stun 5 }

		
--  1.3.6.1.4.1.37950.1.1.6.2.1.8.20.2.6
		-- 1.3.6.1.4.1.37950.1.1.6.2.1.8.20.2.6
		stunServerPassword OBJECT-TYPE
			SYNTAX OCTET STRING (SIZE (0..64))
			MAX-ACCESS read-write
			STATUS current
			DESCRIPTION
				"Description."
			::= { onuTr069Stun 6 }

		
--  1.3.6.1.4.1.37950.1.1.6.2.1.8.20.2.7
		-- 1.3.6.1.4.1.37950.1.1.6.2.1.8.20.2.7
		stunAction OBJECT-TYPE
			SYNTAX INTEGER
				{
				submit(1),
				remove(2)
				}
			MAX-ACCESS read-write
			STATUS current
			DESCRIPTION
				"Description."
			::= { onuTr069Stun 7 }

		
--  1.3.6.1.4.1.37950.1.1.6.2.1.8.21
		-- 1.3.6.1.4.1.37950.1.1.6.2.1.8.21
		priPNatType OBJECT IDENTIFIER ::= { v1600gPriProfileCfg 21 }

		
--  1.3.6.1.4.1.37950.1.1.6.2.1.8.21.1
		-- 1.3.6.1.4.1.37950.1.1.6.2.1.8.21.1
		priPNatTypePID OBJECT-TYPE
			SYNTAX Integer32
			MAX-ACCESS read-write
			STATUS current
			DESCRIPTION
				"Description."
			::= { priPNatType 1 }

		
--     1.3.6.1.4.1.37950.1.1.5.12.8.3.39.1
-- 1.3.6.1.4.1.37950.1.1.5.12.8.3.39.1
-- 1.3.6.1.4.1.37950.1.1.5.12.8.3.39.1
-- 1.3.6.1.4.1.37950.1.1.6.2.1.8.21.2
		-- 1.3.6.1.4.1.37950.1.1.6.2.1.8.21.2
		natType OBJECT-TYPE
			SYNTAX INTEGER
				{
				nat1(1),
				nat2(2),
				nat3(3),
				nat4-napt(4)
				}
			MAX-ACCESS read-write
			STATUS current
			DESCRIPTION
				"Description."
			::= { priPNatType 2 }

		
--  1.3.6.1.4.1.37950.1.1.6.2.1.8.21.3
		-- 1.3.6.1.4.1.37950.1.1.6.2.1.8.21.3
		natTypeAction OBJECT-TYPE
			SYNTAX INTEGER { submit(1) }
			MAX-ACCESS read-write
			STATUS current
			DESCRIPTION
				"Description."
			::= { priPNatType 3 }

		
--  1.3.6.1.4.1.37950.1.1.6.2.1.8.22
		-- 1.3.6.1.4.1.37950.1.1.6.2.1.8.22
		priPUPnP OBJECT IDENTIFIER ::= { v1600gPriProfileCfg 22 }

		
--  1.3.6.1.4.1.37950.1.1.6.2.1.8.22.1
		-- 1.3.6.1.4.1.37950.1.1.6.2.1.8.22.1
		priPUPnPPID OBJECT-TYPE
			SYNTAX Integer32
			MAX-ACCESS read-write
			STATUS current
			DESCRIPTION
				"Description."
			::= { priPUPnP 1 }

		
--  1.3.6.1.4.1.37950.1.1.6.2.1.8.22.2
		-- 1.3.6.1.4.1.37950.1.1.6.2.1.8.22.2
		upnpStatus OBJECT-TYPE
			SYNTAX INTEGER
				{
				disable(0),
				enable(1)
				}
			MAX-ACCESS read-write
			STATUS current
			DESCRIPTION
				"Description."
			::= { priPUPnP 2 }

		
--  1.3.6.1.4.1.37950.1.1.6.2.1.8.22.3
		-- 1.3.6.1.4.1.37950.1.1.6.2.1.8.22.3
		upnpWanIndex OBJECT-TYPE
			SYNTAX Integer32 (1..8)
			MAX-ACCESS read-write
			STATUS current
			DESCRIPTION
				"Description."
			::= { priPUPnP 3 }

		
--  1.3.6.1.4.1.37950.1.1.6.2.1.8.22.4
		-- 1.3.6.1.4.1.37950.1.1.6.2.1.8.22.4
		upnpAction OBJECT-TYPE
			SYNTAX INTEGER { submit(1) }
			MAX-ACCESS read-write
			STATUS current
			DESCRIPTION
				"Description."
			::= { priPUPnP 4 }

		
--  1.3.6.1.4.1.37950.1.1.6.2.1.8.23
		-- 1.3.6.1.4.1.37950.1.1.6.2.1.8.23
		priPH248Server OBJECT IDENTIFIER ::= { v1600gPriProfileCfg 23 }

		
--  1.3.6.1.4.1.37950.1.1.6.2.1.8.23.1
		-- 1.3.6.1.4.1.37950.1.1.6.2.1.8.23.1
		h248SrvPID OBJECT-TYPE
			SYNTAX Integer32
			MAX-ACCESS read-write
			STATUS current
			DESCRIPTION
				"Description."
			::= { priPH248Server 1 }

		
--  1.3.6.1.4.1.37950.1.1.6.2.1.8.23.2
		-- 1.3.6.1.4.1.37950.1.1.6.2.1.8.23.2
		h248SrvMGPort OBJECT-TYPE
			SYNTAX Integer32 (1..65535)
			MAX-ACCESS read-write
			STATUS current
			DESCRIPTION
				"Description."
			DEFVAL { 2944 }
			::= { priPH248Server 2 }

		
--  1.3.6.1.4.1.37950.1.1.6.2.1.8.23.3
		-- 1.3.6.1.4.1.37950.1.1.6.2.1.8.23.3
		h248SrvMGCServer OBJECT-TYPE
			SYNTAX OCTET STRING (SIZE (1..64))
			MAX-ACCESS read-write
			STATUS current
			DESCRIPTION
				"Description."
			::= { priPH248Server 3 }

		
--  1.3.6.1.4.1.37950.1.1.6.2.1.8.23.4
		-- 1.3.6.1.4.1.37950.1.1.6.2.1.8.23.4
		h248SrvMGCPort OBJECT-TYPE
			SYNTAX Integer32 (1..65535)
			MAX-ACCESS read-write
			STATUS current
			DESCRIPTION
				"Description."
			DEFVAL { 2944 }
			::= { priPH248Server 4 }

		
--  1.3.6.1.4.1.37950.1.1.6.2.1.8.23.5
		-- 1.3.6.1.4.1.37950.1.1.6.2.1.8.23.5
		h248SrvBackupMGCServer OBJECT-TYPE
			SYNTAX OCTET STRING (SIZE (0..64))
			MAX-ACCESS read-write
			STATUS current
			DESCRIPTION
				"Description."
			::= { priPH248Server 5 }

		
--  1.3.6.1.4.1.37950.1.1.6.2.1.8.23.6
		-- 1.3.6.1.4.1.37950.1.1.6.2.1.8.23.6
		h248SrvBackupMGCPort OBJECT-TYPE
			SYNTAX Integer32 (0..65535)
			MAX-ACCESS read-write
			STATUS current
			DESCRIPTION
				"Description."
			::= { priPH248Server 6 }

		
--  1.3.6.1.4.1.37950.1.1.6.2.1.8.23.7
		-- 1.3.6.1.4.1.37950.1.1.6.2.1.8.23.7
		h248SrvRegisterMode OBJECT-TYPE
			SYNTAX INTEGER
				{
				ip_address(0),
				domain_name(1),
				device_name(2)
				}
			MAX-ACCESS read-write
			STATUS current
			DESCRIPTION
				"Description."
			::= { priPH248Server 7 }

		
--  1.3.6.1.4.1.37950.1.1.6.2.1.8.23.8
		-- 1.3.6.1.4.1.37950.1.1.6.2.1.8.23.8
		h248SrvMID OBJECT-TYPE
			SYNTAX OCTET STRING (SIZE (0..64))
			MAX-ACCESS read-write
			STATUS current
			DESCRIPTION
				"Description."
			::= { priPH248Server 8 }

		
--  1.3.6.1.4.1.37950.1.1.6.2.1.8.23.9
		-- 1.3.6.1.4.1.37950.1.1.6.2.1.8.23.9
		h248SrvHeartbeatMode OBJECT-TYPE
			SYNTAX INTEGER
				{
				disable(0),
				active_enable(1),
				passive_enable(2)
				}
			MAX-ACCESS read-write
			STATUS current
			DESCRIPTION
				"Description."
			::= { priPH248Server 9 }

		
--  1.3.6.1.4.1.37950.1.1.6.2.1.8.23.10
		-- 1.3.6.1.4.1.37950.1.1.6.2.1.8.23.10
		h248SrvHeartbeatFormat OBJECT-TYPE
			SYNTAX INTEGER
				{
				notify(1),
				service_change(2)
				}
			MAX-ACCESS read-write
			STATUS current
			DESCRIPTION
				"Description."
			::= { priPH248Server 10 }

		
--  1.3.6.1.4.1.37950.1.1.6.2.1.8.23.11
		-- 1.3.6.1.4.1.37950.1.1.6.2.1.8.23.11
		h248SrvHeartbeatCycle OBJECT-TYPE
			SYNTAX Integer32 (1..65535)
			MAX-ACCESS read-write
			STATUS current
			DESCRIPTION
				"Description."
			DEFVAL { 60 }
			::= { priPH248Server 11 }

		
--  1.3.6.1.4.1.37950.1.1.6.2.1.8.23.12
		-- 1.3.6.1.4.1.37950.1.1.6.2.1.8.23.12
		h248SrvHeartbeatCount OBJECT-TYPE
			SYNTAX Integer32 (1..255)
			MAX-ACCESS read-write
			STATUS current
			DESCRIPTION
				"Description."
			DEFVAL { 3 }
			::= { priPH248Server 12 }

		
--  1.3.6.1.4.1.37950.1.1.6.2.1.8.23.13
		-- 1.3.6.1.4.1.37950.1.1.6.2.1.8.23.13
		h248SrvAction OBJECT-TYPE
			SYNTAX INTEGER { submit(1) }
			MAX-ACCESS read-write
			STATUS current
			DESCRIPTION
				"Description."
			::= { priPH248Server 13 }

		
--  1.3.6.1.4.1.37950.1.1.6.2.1.8.24
		-- 1.3.6.1.4.1.37950.1.1.6.2.1.8.24
		priPH248User OBJECT IDENTIFIER ::= { v1600gPriProfileCfg 24 }

		
--  1.3.6.1.4.1.37950.1.1.6.2.1.8.24.1
		-- 1.3.6.1.4.1.37950.1.1.6.2.1.8.24.1
		h248UserPID OBJECT-TYPE
			SYNTAX Integer32
			MAX-ACCESS read-write
			STATUS current
			DESCRIPTION
				"Description."
			::= { priPH248User 1 }

		
--  1.3.6.1.4.1.37950.1.1.6.2.1.8.24.2
		-- 1.3.6.1.4.1.37950.1.1.6.2.1.8.24.2
		h248UserPortIndex OBJECT-TYPE
			SYNTAX Integer32 (1..8)
			MAX-ACCESS read-write
			STATUS current
			DESCRIPTION
				"Description."
			::= { priPH248User 2 }

		
--  1.3.6.1.4.1.37950.1.1.6.2.1.8.24.3
		-- 1.3.6.1.4.1.37950.1.1.6.2.1.8.24.3
		h248UserName OBJECT-TYPE
			SYNTAX OCTET STRING (SIZE (0..64))
			MAX-ACCESS read-write
			STATUS current
			DESCRIPTION
				"Description."
			::= { priPH248User 3 }

		
--  1.3.6.1.4.1.37950.1.1.6.2.1.8.24.4
		-- 1.3.6.1.4.1.37950.1.1.6.2.1.8.24.4
		h248UserAction OBJECT-TYPE
			SYNTAX INTEGER { submit(1) }
			MAX-ACCESS read-write
			STATUS current
			DESCRIPTION
				"Description."
			::= { priPH248User 4 }

		
--  1.3.6.1.4.1.37950.1.1.6.2.1.8.25
		-- 1.3.6.1.4.1.37950.1.1.6.2.1.8.25
		priPH248SignalMediaAlone OBJECT IDENTIFIER ::= { v1600gPriProfileCfg 25 }

		
--  1.3.6.1.4.1.37950.1.1.6.2.1.8.25.1
		-- 1.3.6.1.4.1.37950.1.1.6.2.1.8.25.1
		priPH248SMAPID OBJECT-TYPE
			SYNTAX Integer32
			MAX-ACCESS read-write
			STATUS current
			DESCRIPTION
				"Description."
			::= { priPH248SignalMediaAlone 1 }

		
--  1.3.6.1.4.1.37950.1.1.6.2.1.8.25.2
		-- 1.3.6.1.4.1.37950.1.1.6.2.1.8.25.2
		priPH248SMAStatus OBJECT-TYPE
			SYNTAX INTEGER
				{
				disable(0),
				enable(1)
				}
			MAX-ACCESS read-write
			STATUS current
			DESCRIPTION
				"Description."
			::= { priPH248SignalMediaAlone 2 }

		
--  1.3.6.1.4.1.37950.1.1.6.2.1.8.25.3
		-- 1.3.6.1.4.1.37950.1.1.6.2.1.8.25.3
		priPH248SMAWanIndex OBJECT-TYPE
			SYNTAX Integer32 (1..8)
			MAX-ACCESS read-write
			STATUS current
			DESCRIPTION
				"Description."
			::= { priPH248SignalMediaAlone 3 }

		
--  1.3.6.1.4.1.37950.1.1.6.2.1.8.25.4
		-- 1.3.6.1.4.1.37950.1.1.6.2.1.8.25.4
		priPH248SMAAction OBJECT-TYPE
			SYNTAX INTEGER { submit(1) }
			MAX-ACCESS read-write
			STATUS current
			DESCRIPTION
				"Description."
			::= { priPH248SignalMediaAlone 4 }

		
--  1.3.6.1.4.1.37950.1.1.6.2.1.8.26
		-- 1.3.6.1.4.1.37950.1.1.6.2.1.8.26
		priPMacAclRule OBJECT IDENTIFIER ::= { v1600gPriProfileCfg 26 }

		
--  1.3.6.1.4.1.37950.1.1.6.2.1.8.26.1
		-- 1.3.6.1.4.1.37950.1.1.6.2.1.8.26.1
		priPMRulePID OBJECT-TYPE
			SYNTAX Integer32
			MAX-ACCESS read-write
			STATUS current
			DESCRIPTION
				"Description."
			::= { priPMacAclRule 1 }

		
--  1.3.6.1.4.1.37950.1.1.6.2.1.8.26.2
		-- 1.3.6.1.4.1.37950.1.1.6.2.1.8.26.2
		priPMRuleStatus OBJECT-TYPE
			SYNTAX INTEGER
				{
				disable(0),
				enable(1)
				}
			MAX-ACCESS read-write
			STATUS current
			DESCRIPTION
				"Description."
			::= { priPMacAclRule 2 }

		
--  1.3.6.1.4.1.37950.1.1.6.2.1.8.26.3
		-- 1.3.6.1.4.1.37950.1.1.6.2.1.8.26.3
		priPMRuleMode OBJECT-TYPE
			SYNTAX INTEGER { whitelist(0) }
			MAX-ACCESS read-write
			STATUS current
			DESCRIPTION
				"Description."
			::= { priPMacAclRule 3 }

		
--  1.3.6.1.4.1.37950.1.1.6.2.1.8.26.4
		-- 1.3.6.1.4.1.37950.1.1.6.2.1.8.26.4
		priPMRuleAction OBJECT-TYPE
			SYNTAX INTEGER { submit(1) }
			MAX-ACCESS read-write
			STATUS current
			DESCRIPTION
				"Description."
			::= { priPMacAclRule 4 }

		
--  1.3.6.1.4.1.37950.1.1.6.2.1.8.27
		-- 1.3.6.1.4.1.37950.1.1.6.2.1.8.27
		priPMacAclGroup OBJECT IDENTIFIER ::= { v1600gPriProfileCfg 27 }

		
--  1.3.6.1.4.1.37950.1.1.6.2.1.8.27.1
		-- 1.3.6.1.4.1.37950.1.1.6.2.1.8.27.1
		priPMGroupPID OBJECT-TYPE
			SYNTAX Integer32
			MAX-ACCESS read-write
			STATUS current
			DESCRIPTION
				"Description."
			::= { priPMacAclGroup 1 }

		
--  1.3.6.1.4.1.37950.1.1.6.2.1.8.27.2
		-- 1.3.6.1.4.1.37950.1.1.6.2.1.8.27.2
		priPMGroupGroupNum OBJECT-TYPE
			SYNTAX Integer32 (1..32)
			MAX-ACCESS read-write
			STATUS current
			DESCRIPTION
				"Description."
			::= { priPMacAclGroup 2 }

		
--  1.3.6.1.4.1.37950.1.1.6.2.1.8.27.3
		-- 1.3.6.1.4.1.37950.1.1.6.2.1.8.27.3
		priPMGroupMAC OBJECT-TYPE
			SYNTAX OCTET STRING
			MAX-ACCESS read-write
			STATUS current
			DESCRIPTION
				"Description."
			::= { priPMacAclGroup 3 }

		
--  1.3.6.1.4.1.37950.1.1.6.2.1.8.27.4
		-- 1.3.6.1.4.1.37950.1.1.6.2.1.8.27.4
		priPMGroupMask OBJECT-TYPE
			SYNTAX OCTET STRING
			MAX-ACCESS read-write
			STATUS current
			DESCRIPTION
				"Description."
			::= { priPMacAclGroup 4 }

		
--  1.3.6.1.4.1.37950.1.1.6.2.1.8.27.5
		-- 1.3.6.1.4.1.37950.1.1.6.2.1.8.27.5
		priPMGroupAction OBJECT-TYPE
			SYNTAX INTEGER
				{
				add(1),
				delete(2),
				clear(3)
				}
			MAX-ACCESS read-write
			STATUS current
			DESCRIPTION
				"Description."
			::= { priPMacAclGroup 5 }

		
--  1.3.6.1.4.1.37950.1.1.6.2.1.8.28
		-- 1.3.6.1.4.1.37950.1.1.6.2.1.8.28
		priPMQTT OBJECT IDENTIFIER ::= { v1600gPriProfileCfg 28 }

		
--  1.3.6.1.4.1.37950.1.1.6.2.1.8.28.1
		-- 1.3.6.1.4.1.37950.1.1.6.2.1.8.28.1
		priPMQTTPID OBJECT-TYPE
			SYNTAX Integer32
			MAX-ACCESS read-write
			STATUS current
			DESCRIPTION
				"Description."
			::= { priPMQTT 1 }

		
--  1.3.6.1.4.1.37950.1.1.6.2.1.8.28.2
		-- 1.3.6.1.4.1.37950.1.1.6.2.1.8.28.2
		priPMQTTEnableStatus OBJECT-TYPE
			SYNTAX INTEGER
				{
				disable(0),
				enable(1)
				}
			MAX-ACCESS read-write
			STATUS current
			DESCRIPTION
				"Description."
			::= { priPMQTT 2 }

		
--  1.3.6.1.4.1.37950.1.1.6.2.1.8.28.3
		-- 1.3.6.1.4.1.37950.1.1.6.2.1.8.28.3
		priPMQTTAddress OBJECT-TYPE
			SYNTAX OCTET STRING
			MAX-ACCESS read-write
			STATUS current
			DESCRIPTION
				"Description."
			::= { priPMQTT 3 }

		
--  1.3.6.1.4.1.37950.1.1.6.2.1.8.28.4
		-- 1.3.6.1.4.1.37950.1.1.6.2.1.8.28.4
		priPMQTTUserName OBJECT-TYPE
			SYNTAX OCTET STRING
			MAX-ACCESS read-write
			STATUS current
			DESCRIPTION
				"Description."
			::= { priPMQTT 4 }

		
--  1.3.6.1.4.1.37950.1.1.6.2.1.8.28.5
		-- 1.3.6.1.4.1.37950.1.1.6.2.1.8.28.5
		priPMQTTPassword OBJECT-TYPE
			SYNTAX OCTET STRING
			MAX-ACCESS read-write
			STATUS current
			DESCRIPTION
				"Description."
			::= { priPMQTT 5 }

		
--  1.3.6.1.4.1.37950.1.1.6.2.1.8.28.6
		-- 1.3.6.1.4.1.37950.1.1.6.2.1.8.28.6
		priPMQTTAction OBJECT-TYPE
			SYNTAX INTEGER { submit(1) }
			MAX-ACCESS read-write
			STATUS current
			DESCRIPTION
				"Description."
			::= { priPMQTT 6 }

		
--  1.3.6.1.4.1.37950.1.1.6.2.1.8.28.7
		-- 1.3.6.1.4.1.37950.1.1.6.2.1.8.28.7
		priPMQTTID OBJECT-TYPE
			SYNTAX OCTET STRING
			MAX-ACCESS read-write
			STATUS current
			DESCRIPTION
				"Description."
			::= { priPMQTT 7 }

		
		-- 1.3.6.1.4.1.37950.1.1.6.2.1.8.29
		priPAP OBJECT IDENTIFIER ::= { v1600gPriProfileCfg 29 }

		
		-- 1.3.6.1.4.1.37950.1.1.6.2.1.8.29.1
		priPAPPID OBJECT-TYPE
			SYNTAX Integer32
			MAX-ACCESS read-write
			STATUS current
			DESCRIPTION
				"Description."
			::= { priPAP 1 }

		
		-- 1.3.6.1.4.1.37950.1.1.6.2.1.8.29.2
		priPAPStatus OBJECT-TYPE
			SYNTAX INTEGER
				{
				disable(0),
				enable(1)
				}
			MAX-ACCESS read-write
			STATUS current
			DESCRIPTION
				"Description."
			::= { priPAP 2 }

		
		-- 1.3.6.1.4.1.37950.1.1.6.2.1.8.29.3
		priPAPAction OBJECT-TYPE
			SYNTAX INTEGER { submit(1) }
			MAX-ACCESS read-write
			STATUS current
			DESCRIPTION
				"Description."
			::= { priPAP 3 }

		
		-- 1.3.6.1.4.1.37950.1.1.6.2.1.8.29.4
		priPAPVLAN OBJECT-TYPE
			SYNTAX Integer32 (0..4095)
			MAX-ACCESS read-write
			STATUS current
			DESCRIPTION
				"Description."
			::= { priPAP 4 }

		
--  1.3.6.1.4.1.37950.1.1.6.2.1.9
		-- 1.3.6.1.4.1.37950.1.1.6.2.1.9
		v1600gIGMPProfileCfg OBJECT IDENTIFIER ::= { v1600gProfileCfg 9 }

		
--  1.3.6.1.4.1.37950.1.1.6.2.1.9.1
		-- 1.3.6.1.4.1.37950.1.1.6.2.1.9.1
		v1600gIGMPProfileAdd OBJECT IDENTIFIER ::= { v1600gIGMPProfileCfg 1 }

		
--  1.3.6.1.4.1.37950.1.1.6.2.1.9.1.1
		-- 1.3.6.1.4.1.37950.1.1.6.2.1.9.1.1
		igmpPName OBJECT-TYPE
			SYNTAX OCTET STRING
			MAX-ACCESS read-write
			STATUS current
			DESCRIPTION
				"Description."
			::= { v1600gIGMPProfileAdd 1 }

		
--  1.3.6.1.4.1.37950.1.1.6.2.1.9.1.2
		-- 1.3.6.1.4.1.37950.1.1.6.2.1.9.1.2
		igmpPNameAction OBJECT-TYPE
			SYNTAX INTEGER
				{
				add(1),
				del(2),
				commit(3)
				}
			MAX-ACCESS read-write
			STATUS current
			DESCRIPTION
				"Description."
			::= { v1600gIGMPProfileAdd 2 }

		
--  1.3.6.1.4.1.37950.1.1.6.2.1.9.2
		-- 1.3.6.1.4.1.37950.1.1.6.2.1.9.2
		igmpProfileID OBJECT-TYPE
			SYNTAX Integer32
			MAX-ACCESS read-write
			STATUS current
			DESCRIPTION
				"Description."
			::= { v1600gIGMPProfileCfg 2 }

		
--  1.3.6.1.4.1.37950.1.1.6.2.1.9.3
		-- 1.3.6.1.4.1.37950.1.1.6.2.1.9.3
		igmpVersion OBJECT-TYPE
			SYNTAX INTEGER
				{
				v1(1),
				v2(2),
				v3(3)
				}
			MAX-ACCESS read-write
			STATUS current
			DESCRIPTION
				"Description."
			::= { v1600gIGMPProfileCfg 3 }

		
--  1.3.6.1.4.1.37950.1.1.6.2.1.9.4
		-- 1.3.6.1.4.1.37950.1.1.6.2.1.9.4
		igmpMode OBJECT-TYPE
			SYNTAX INTEGER
				{
				snooping(1),
				spr(2),
				proxy(3),
				flood(4)
				}
			MAX-ACCESS read-write
			STATUS current
			DESCRIPTION
				"Description."
			::= { v1600gIGMPProfileCfg 4 }

		
--  1.3.6.1.4.1.37950.1.1.6.2.1.9.5
		-- 1.3.6.1.4.1.37950.1.1.6.2.1.9.5
		igmpFastLeave OBJECT-TYPE
			SYNTAX INTEGER
				{
				disable(1),
				enable(2)
				}
			MAX-ACCESS read-write
			STATUS current
			DESCRIPTION
				"Description."
			::= { v1600gIGMPProfileCfg 5 }

		
--  1.3.6.1.4.1.37950.1.1.6.2.1.9.6
		-- 1.3.6.1.4.1.37950.1.1.6.2.1.9.6
		igmpNotMatchGroup OBJECT-TYPE
			SYNTAX INTEGER
				{
				discard(1),
				forward(2)
				}
			MAX-ACCESS read-write
			STATUS current
			DESCRIPTION
				"Description."
			::= { v1600gIGMPProfileCfg 6 }

		
--  1.3.6.1.4.1.37950.1.1.6.2.1.9.7
		-- 1.3.6.1.4.1.37950.1.1.6.2.1.9.7
		igmpRobustness OBJECT-TYPE
			SYNTAX Integer32 (1..255)
			MAX-ACCESS read-write
			STATUS current
			DESCRIPTION
				"Description."
			::= { v1600gIGMPProfileCfg 7 }

		
--  1.3.6.1.4.1.37950.1.1.6.2.1.9.8
		-- 1.3.6.1.4.1.37950.1.1.6.2.1.9.8
		igmpProxyIP OBJECT-TYPE
			SYNTAX IpAddress
			MAX-ACCESS read-write
			STATUS current
			DESCRIPTION
				"Description."
			::= { v1600gIGMPProfileCfg 8 }

		
--  1.3.6.1.4.1.37950.1.1.6.2.1.9.9
		-- 1.3.6.1.4.1.37950.1.1.6.2.1.9.9
		igmpQueryInterval OBJECT-TYPE
			SYNTAX Unsigned32 (0..4294967294)
			MAX-ACCESS read-write
			STATUS current
			DESCRIPTION
				"Description."
			::= { v1600gIGMPProfileCfg 9 }

		
--  1.3.6.1.4.1.37950.1.1.6.2.1.9.10
		-- 1.3.6.1.4.1.37950.1.1.6.2.1.9.10
		igmpQueryMaxresp OBJECT-TYPE
			SYNTAX Unsigned32 (0..4294967294)
			MAX-ACCESS read-write
			STATUS current
			DESCRIPTION
				"Description."
			::= { v1600gIGMPProfileCfg 10 }

		
--  1.3.6.1.4.1.37950.1.1.6.2.1.9.11
		-- 1.3.6.1.4.1.37950.1.1.6.2.1.9.11
		igmpQueryLastInterval OBJECT-TYPE
			SYNTAX Unsigned32 (0..4294967294)
			MAX-ACCESS read-write
			STATUS current
			DESCRIPTION
				"Description."
			::= { v1600gIGMPProfileCfg 11 }

		
--  1.3.6.1.4.1.37950.1.1.6.2.1.9.12
		-- 1.3.6.1.4.1.37950.1.1.6.2.1.9.12
		igmpRateLimit OBJECT-TYPE
			SYNTAX Unsigned32 (0..4294967294)
			MAX-ACCESS read-write
			STATUS current
			DESCRIPTION
				"Description."
			::= { v1600gIGMPProfileCfg 12 }

		
--  1.3.6.1.4.1.37950.1.1.6.2.1.9.13
		-- 1.3.6.1.4.1.37950.1.1.6.2.1.9.13
		v1600gxbIgmpProfileCfg OBJECT IDENTIFIER ::= { v1600gIGMPProfileCfg 13 }

		
--  1.3.6.1.4.1.37950.1.1.6.2.1.9.13.1
		-- 1.3.6.1.4.1.37950.1.1.6.2.1.9.13.1
		gxbIgmpProfileID OBJECT-TYPE
			SYNTAX Integer32
			MAX-ACCESS read-write
			STATUS current
			DESCRIPTION
				"Description."
			::= { v1600gxbIgmpProfileCfg 1 }

		
--  1.3.6.1.4.1.37950.1.1.6.2.1.9.13.2
		-- 1.3.6.1.4.1.37950.1.1.6.2.1.9.13.2
		gxbIgmpVersion OBJECT-TYPE
			SYNTAX INTEGER
				{
				igmp_v1(1),
				igmp_v2(2),
				igmp_v3(3),
				mld_v1(16),
				mld_v2(17)
				}
			MAX-ACCESS read-write
			STATUS current
			DESCRIPTION
				"Description."
			::= { v1600gxbIgmpProfileCfg 2 }

		
--  1.3.6.1.4.1.37950.1.1.6.2.1.9.13.3
		-- 1.3.6.1.4.1.37950.1.1.6.2.1.9.13.3
		gxbIgmpMode OBJECT-TYPE
			SYNTAX INTEGER
				{
				snooping(0),
				spr(1),
				proxy(2)
				}
			MAX-ACCESS read-write
			STATUS current
			DESCRIPTION
				"Description."
			::= { v1600gxbIgmpProfileCfg 3 }

		
--  1.3.6.1.4.1.37950.1.1.6.2.1.9.13.4
		-- 1.3.6.1.4.1.37950.1.1.6.2.1.9.13.4
		gxbIgmpFastLeave OBJECT-TYPE
			SYNTAX INTEGER
				{
				disable(0),
				enable(1)
				}
			MAX-ACCESS read-write
			STATUS current
			DESCRIPTION
				"Description."
			::= { v1600gxbIgmpProfileCfg 4 }

		
--  1.3.6.1.4.1.37950.1.1.6.2.1.9.13.5
		-- 1.3.6.1.4.1.37950.1.1.6.2.1.9.13.5
		gxbIgmpUpstreamTagControl OBJECT-TYPE
			SYNTAX INTEGER
				{
				transparent(0),
				add_vlan_tag(1),
				replace_vlan_tag(2),
				replace_vlan_id(3)
				}
			MAX-ACCESS read-write
			STATUS current
			DESCRIPTION
				"Description."
			::= { v1600gxbIgmpProfileCfg 5 }

		
--  1.3.6.1.4.1.37950.1.1.6.2.1.9.13.6
		-- 1.3.6.1.4.1.37950.1.1.6.2.1.9.13.6
		gxbIgmpUpstreamTciVlan OBJECT-TYPE
			SYNTAX Integer32 (1..4094)
			MAX-ACCESS read-write
			STATUS current
			DESCRIPTION
				"Description."
			::= { v1600gxbIgmpProfileCfg 6 }

		
--  1.3.6.1.4.1.37950.1.1.6.2.1.9.13.7
		-- 1.3.6.1.4.1.37950.1.1.6.2.1.9.13.7
		gxbIgmpUpstreamTciPBits OBJECT-TYPE
			SYNTAX Integer32 (0..7)
			MAX-ACCESS read-write
			STATUS current
			DESCRIPTION
				"Description."
			::= { v1600gxbIgmpProfileCfg 7 }

		
--  1.3.6.1.4.1.37950.1.1.6.2.1.9.13.8
		-- 1.3.6.1.4.1.37950.1.1.6.2.1.9.13.8
		gxbIgmpRateLimit OBJECT-TYPE
			SYNTAX Unsigned32 (0..4294967294)
			MAX-ACCESS read-write
			STATUS current
			DESCRIPTION
				"Description."
			::= { v1600gxbIgmpProfileCfg 8 }

		
--  1.3.6.1.4.1.37950.1.1.6.2.1.9.13.9
		-- 1.3.6.1.4.1.37950.1.1.6.2.1.9.13.9
		gxbIgmpRobustness OBJECT-TYPE
			SYNTAX Integer32 (0..255)
			MAX-ACCESS read-write
			STATUS current
			DESCRIPTION
				"Description."
			::= { v1600gxbIgmpProfileCfg 9 }

		
--  1.3.6.1.4.1.37950.1.1.6.2.1.9.13.10
		-- 1.3.6.1.4.1.37950.1.1.6.2.1.9.13.10
		gxbIgmpProxyIP OBJECT-TYPE
			SYNTAX IpAddress
			MAX-ACCESS read-write
			STATUS current
			DESCRIPTION
				"Description."
			::= { v1600gxbIgmpProfileCfg 10 }

		
--  1.3.6.1.4.1.37950.1.1.6.2.1.9.13.11
		-- 1.3.6.1.4.1.37950.1.1.6.2.1.9.13.11
		gxbIgmpQueryInterval OBJECT-TYPE
			SYNTAX Unsigned32 (0..4294967294)
			MAX-ACCESS read-write
			STATUS current
			DESCRIPTION
				"Description."
			::= { v1600gxbIgmpProfileCfg 11 }

		
--  1.3.6.1.4.1.37950.1.1.6.2.1.9.13.12
		-- 1.3.6.1.4.1.37950.1.1.6.2.1.9.13.12
		gxbIgmpQueryMaxresp OBJECT-TYPE
			SYNTAX Unsigned32 (0..4294967294)
			MAX-ACCESS read-write
			STATUS current
			DESCRIPTION
				"Description."
			::= { v1600gxbIgmpProfileCfg 12 }

		
--  1.3.6.1.4.1.37950.1.1.6.2.1.9.13.13
		-- 1.3.6.1.4.1.37950.1.1.6.2.1.9.13.13
		gxbIgmpQueryLastInterval OBJECT-TYPE
			SYNTAX Unsigned32 (0..4294967294)
			MAX-ACCESS read-write
			STATUS current
			DESCRIPTION
				"Description."
			::= { v1600gxbIgmpProfileCfg 13 }

		
--  1.3.6.1.4.1.37950.1.1.6.2.1.9.13.14
		-- 1.3.6.1.4.1.37950.1.1.6.2.1.9.13.14
		gxbIgmpDownstreamTagControl OBJECT-TYPE
			SYNTAX INTEGER
				{
				transparent(0),
				strip_outer_tag(1),
				add_outer_tag(2),
				replace_outer_tci(3),
				replace_outer_vid(4),
				add_outer_tag_by_subscriber_conf_info(5),
				replace_outer_tci_by_subscriber_conf_info(6),
				replace_outer_vid_by_subscriber_conf_info(7)
				}
			MAX-ACCESS read-write
			STATUS current
			DESCRIPTION
				"Description."
			::= { v1600gxbIgmpProfileCfg 14 }

		
--  1.3.6.1.4.1.37950.1.1.6.2.1.9.13.15
		-- 1.3.6.1.4.1.37950.1.1.6.2.1.9.13.15
		gxbIgmpDownstreamTciVLAN OBJECT-TYPE
			SYNTAX Integer32 (1..4094)
			MAX-ACCESS read-write
			STATUS current
			DESCRIPTION
				"Description."
			::= { v1600gxbIgmpProfileCfg 15 }

		
--  1.3.6.1.4.1.37950.1.1.6.2.1.9.13.16
		-- 1.3.6.1.4.1.37950.1.1.6.2.1.9.13.16
		gxbIgmpDownstreamTciPBits OBJECT-TYPE
			SYNTAX Integer32 (0..7)
			MAX-ACCESS read-write
			STATUS current
			DESCRIPTION
				"Description."
			::= { v1600gxbIgmpProfileCfg 16 }

		
--  1.3.6.1.4.1.37950.1.1.6.2.1.9.13.17
		-- 1.3.6.1.4.1.37950.1.1.6.2.1.9.13.17
		gxbIgmpNonMatchGroup OBJECT-TYPE
			SYNTAX INTEGER
				{
				discard(0),
				forward(1)
				}
			MAX-ACCESS read-write
			STATUS current
			DESCRIPTION
				"Description."
			::= { v1600gxbIgmpProfileCfg 17 }

		
--  1.3.6.1.4.1.37950.1.1.6.2.1.9.13.18
		-- 1.3.6.1.4.1.37950.1.1.6.2.1.9.13.18
		gxbIgmpAction OBJECT-TYPE
			SYNTAX INTEGER { submit(0) }
			MAX-ACCESS read-write
			STATUS current
			DESCRIPTION
				"Description."
			::= { v1600gxbIgmpProfileCfg 18 }

		
--  1.3.6.1.4.1.37950.1.1.6.2.1.10
		-- 1.3.6.1.4.1.37950.1.1.6.2.1.10
		v1600gFormatProfileCfg OBJECT IDENTIFIER ::= { v1600gProfileCfg 10 }

		
--  1.3.6.1.4.1.37950.1.1.6.2.1.10.1
		-- 1.3.6.1.4.1.37950.1.1.6.2.1.10.1
		fmtPName OBJECT-TYPE
			SYNTAX OCTET STRING
			MAX-ACCESS read-write
			STATUS current
			DESCRIPTION
				"Description."
			::= { v1600gFormatProfileCfg 1 }

		
--  1.3.6.1.4.1.37950.1.1.6.2.1.10.2
		-- 1.3.6.1.4.1.37950.1.1.6.2.1.10.2
		fmtPNameAction OBJECT-TYPE
			SYNTAX INTEGER
				{
				add(1),
				del(2),
				commit(3)
				}
			MAX-ACCESS read-write
			STATUS current
			DESCRIPTION
				"Description."
			::= { v1600gFormatProfileCfg 2 }

		
--  1.3.6.1.4.1.37950.1.1.6.2.1.10.3
		-- 1.3.6.1.4.1.37950.1.1.6.2.1.10.3
		fmtPSwitchCfg OBJECT IDENTIFIER ::= { v1600gFormatProfileCfg 3 }

		
--  1.3.6.1.4.1.37950.1.1.6.2.1.10.3.1
		-- 1.3.6.1.4.1.37950.1.1.6.2.1.10.3.1
		fmtPSwitchProfileId OBJECT-TYPE
			SYNTAX Integer32
			MAX-ACCESS read-write
			STATUS current
			DESCRIPTION
				"Description."
			::= { fmtPSwitchCfg 1 }

		
--  1.3.6.1.4.1.37950.1.1.6.2.1.10.3.2
		-- 1.3.6.1.4.1.37950.1.1.6.2.1.10.3.2
		fmtPOpt82 OBJECT-TYPE
			SYNTAX INTEGER
				{
				disable(0),
				enable(1)
				}
			MAX-ACCESS read-write
			STATUS current
			DESCRIPTION
				"Description."
			::= { fmtPSwitchCfg 2 }

		
--  1.3.6.1.4.1.37950.1.1.6.2.1.10.3.3
		-- 1.3.6.1.4.1.37950.1.1.6.2.1.10.3.3
		fmtPOpt18 OBJECT-TYPE
			SYNTAX INTEGER
				{
				disable(0),
				enable(1)
				}
			MAX-ACCESS read-write
			STATUS current
			DESCRIPTION
				"Description."
			::= { fmtPSwitchCfg 3 }

		
--  1.3.6.1.4.1.37950.1.1.6.2.1.10.3.4
		-- 1.3.6.1.4.1.37950.1.1.6.2.1.10.3.4
		fmtPOpt37 OBJECT-TYPE
			SYNTAX INTEGER
				{
				disable(0),
				enable(1)
				}
			MAX-ACCESS read-write
			STATUS current
			DESCRIPTION
				"Description."
			::= { fmtPSwitchCfg 4 }

		
--  1.3.6.1.4.1.37950.1.1.6.2.1.10.3.5
		-- 1.3.6.1.4.1.37950.1.1.6.2.1.10.3.5
		fmtPPppoePlus OBJECT-TYPE
			SYNTAX INTEGER
				{
				disable(0),
				enable(1)
				}
			MAX-ACCESS read-write
			STATUS current
			DESCRIPTION
				"Description."
			::= { fmtPSwitchCfg 5 }

		
--  1.3.6.1.4.1.37950.1.1.6.2.1.10.3.6
		-- 1.3.6.1.4.1.37950.1.1.6.2.1.10.3.6
		fmtPSwitchAction OBJECT-TYPE
			SYNTAX INTEGER { submit(1) }
			MAX-ACCESS read-write
			STATUS current
			DESCRIPTION
				"Description."
			::= { fmtPSwitchCfg 6 }

		
--  1.3.6.1.4.1.37950.1.1.6.2.1.10.4
		-- 1.3.6.1.4.1.37950.1.1.6.2.1.10.4
		fmtPTypeCfg OBJECT IDENTIFIER ::= { v1600gFormatProfileCfg 4 }

		
--  1.3.6.1.4.1.37950.1.1.6.2.1.10.4.1
		-- 1.3.6.1.4.1.37950.1.1.6.2.1.10.4.1
		fmtPTypeProfileId OBJECT-TYPE
			SYNTAX Integer32
			MAX-ACCESS read-write
			STATUS current
			DESCRIPTION
				"Description."
			::= { fmtPTypeCfg 1 }

		
--  1.3.6.1.4.1.37950.1.1.6.2.1.10.4.2
		-- 1.3.6.1.4.1.37950.1.1.6.2.1.10.4.2
		formatPType OBJECT-TYPE
			SYNTAX INTEGER
				{
				custom(0),
				ctc(1),
				unicom(2)
				}
			MAX-ACCESS read-write
			STATUS current
			DESCRIPTION
				"Description."
			::= { fmtPTypeCfg 2 }

		
--  1.3.6.1.4.1.37950.1.1.6.2.1.10.5
		-- 1.3.6.1.4.1.37950.1.1.6.2.1.10.5
		fmtPIdCfg OBJECT IDENTIFIER ::= { v1600gFormatProfileCfg 5 }

		
--  1.3.6.1.4.1.37950.1.1.6.2.1.10.5.1
		-- 1.3.6.1.4.1.37950.1.1.6.2.1.10.5.1
		fmtPIdProfileId OBJECT-TYPE
			SYNTAX Integer32
			MAX-ACCESS read-write
			STATUS current
			DESCRIPTION
				"Description."
			::= { fmtPIdCfg 1 }

		
--  1.3.6.1.4.1.37950.1.1.6.2.1.10.5.2
		-- 1.3.6.1.4.1.37950.1.1.6.2.1.10.5.2
		formatPId OBJECT-TYPE
			SYNTAX INTEGER
				{
				circuit-id(0),
				remote-id(1)
				}
			MAX-ACCESS read-write
			STATUS current
			DESCRIPTION
				"Description."
			::= { fmtPIdCfg 2 }

		
--  1.3.6.1.4.1.37950.1.1.6.2.1.10.5.3
		-- 1.3.6.1.4.1.37950.1.1.6.2.1.10.5.3
		fmtPIdIndex OBJECT-TYPE
			SYNTAX Integer32 (1..22)
			MAX-ACCESS read-write
			STATUS current
			DESCRIPTION
				"Description."
			::= { fmtPIdCfg 3 }

		
--  1.3.6.1.4.1.37950.1.1.6.2.1.10.5.4
		-- 1.3.6.1.4.1.37950.1.1.6.2.1.10.5.4
		fmtPIdType OBJECT-TYPE
			SYNTAX INTEGER
				{
				cvlan(0),
				devtype(1),
				acnoid(2),
				slotno(3),
				ponno(4),
				onuno(5),
				onutype(6),
				onusn(7),
				end(8),
				oltmac(9),
				onudesc(10),
				onuport(11)
				}
			MAX-ACCESS read-write
			STATUS current
			DESCRIPTION
				"Description."
			::= { fmtPIdCfg 4 }

		
--  1.3.6.1.4.1.37950.1.1.6.2.1.10.5.5
		-- 1.3.6.1.4.1.37950.1.1.6.2.1.10.5.5
		fmtPIdAction OBJECT-TYPE
			SYNTAX INTEGER { submit(1) }
			MAX-ACCESS read-write
			STATUS current
			DESCRIPTION
				"Description."
			::= { fmtPIdCfg 5 }

		
--  1.3.6.1.4.1.37950.1.1.6.2.1.10.5.6
		-- 1.3.6.1.4.1.37950.1.1.6.2.1.10.5.6
		fmtPIdOnuport OBJECT-TYPE
			SYNTAX OCTET STRING
			MAX-ACCESS read-write
			STATUS current
			DESCRIPTION
				"Description."
			::= { fmtPIdCfg 6 }

		
--  1.3.6.1.4.1.37950.1.1.6.2.2
		-- 1.3.6.1.4.1.37950.1.1.6.2.2
		v1600gProfileShow OBJECT IDENTIFIER ::= { v1600gProfile 2 }

		
--  1.3.6.1.4.1.37950.1.1.6.2.2.1
		-- 1.3.6.1.4.1.37950.1.1.6.2.2.1
		v1600gOnuPTable OBJECT-TYPE
			SYNTAX SEQUENCE OF V1600gOnuPEntry
			MAX-ACCESS not-accessible
			STATUS current
			DESCRIPTION
				"Description."
			::= { v1600gProfileShow 1 }

		
--  1.3.6.1.4.1.37950.1.1.6.2.2.1.1
		-- 1.3.6.1.4.1.37950.1.1.6.2.2.1.1
		v1600gOnuPEntry OBJECT-TYPE
			SYNTAX V1600gOnuPEntry
			MAX-ACCESS not-accessible
			STATUS current
			DESCRIPTION
				"Description."
			INDEX { onuPIdShow }
			::= { v1600gOnuPTable 1 }

		
		V1600gOnuPEntry ::=
			SEQUENCE { 
				onuPIdShow
					Integer32,
				onuPNameShow
					OCTET STRING,
				onuPDescShow
					OCTET STRING,
				onuPMaxTcontShow
					Integer32,
				onuPMaxGemportShow
					Integer32,
				onuPMaxEthShow
					Integer32,
				onuPMaxPotsShow
					Integer32,
				onuPMaxIphostShow
					Integer32,
				onuPMaxIpv6hostShow
					Integer32,
				onuPMaxVeipShow
					Integer32,
				onuPSrvN1Show
					Integer32,
				onuPSrv1MShow
					Integer32,
				onuPSrv1PShow
					Integer32,
				onuPWMNOmciShow
					Integer32,
				onuPOmciSendModeShow
					Integer32,
				onuPDMRangeShow
					Integer32,
				v1600gOnuPSrvAbility
					INTEGER
			 }

--  1.3.6.1.4.1.37950.1.1.6.2.2.1.1.1
		-- 1.3.6.1.4.1.37950.1.1.6.2.2.1.1.1
		onuPIdShow OBJECT-TYPE
			SYNTAX Integer32
			MAX-ACCESS read-only
			STATUS current
			DESCRIPTION
				"Description."
			::= { v1600gOnuPEntry 1 }

		
--  1.3.6.1.4.1.37950.1.1.6.2.2.1.1.2
		-- 1.3.6.1.4.1.37950.1.1.6.2.2.1.1.2
		onuPNameShow OBJECT-TYPE
			SYNTAX OCTET STRING
			MAX-ACCESS read-only
			STATUS current
			DESCRIPTION
				"Description."
			::= { v1600gOnuPEntry 2 }

		
--  1.3.6.1.4.1.37950.1.1.6.2.2.1.1.3
		-- 1.3.6.1.4.1.37950.1.1.6.2.2.1.1.3
		onuPDescShow OBJECT-TYPE
			SYNTAX OCTET STRING
			MAX-ACCESS read-only
			STATUS current
			DESCRIPTION
				"Description."
			::= { v1600gOnuPEntry 3 }

		
--  1.3.6.1.4.1.37950.1.1.6.2.2.1.1.4
		-- 1.3.6.1.4.1.37950.1.1.6.2.2.1.1.4
		onuPMaxTcontShow OBJECT-TYPE
			SYNTAX Integer32
			MAX-ACCESS read-only
			STATUS current
			DESCRIPTION
				"Description."
			::= { v1600gOnuPEntry 4 }

		
--  1.3.6.1.4.1.37950.1.1.6.2.2.1.1.5
		-- 1.3.6.1.4.1.37950.1.1.6.2.2.1.1.5
		onuPMaxGemportShow OBJECT-TYPE
			SYNTAX Integer32
			MAX-ACCESS read-only
			STATUS current
			DESCRIPTION
				"Description."
			::= { v1600gOnuPEntry 5 }

		
--  1.3.6.1.4.1.37950.1.1.6.2.2.1.1.6
		-- 1.3.6.1.4.1.37950.1.1.6.2.2.1.1.6
		onuPMaxEthShow OBJECT-TYPE
			SYNTAX Integer32
			MAX-ACCESS read-only
			STATUS current
			DESCRIPTION
				"Description."
			::= { v1600gOnuPEntry 6 }

		
--  1.3.6.1.4.1.37950.1.1.6.2.2.1.1.7
		-- 1.3.6.1.4.1.37950.1.1.6.2.2.1.1.7
		onuPMaxPotsShow OBJECT-TYPE
			SYNTAX Integer32
			MAX-ACCESS read-only
			STATUS current
			DESCRIPTION
				"Description."
			::= { v1600gOnuPEntry 7 }

		
--  1.3.6.1.4.1.37950.1.1.6.2.2.1.1.8
		-- 1.3.6.1.4.1.37950.1.1.6.2.2.1.1.8
		onuPMaxIphostShow OBJECT-TYPE
			SYNTAX Integer32
			MAX-ACCESS read-only
			STATUS current
			DESCRIPTION
				"Description."
			::= { v1600gOnuPEntry 8 }

		
--  1.3.6.1.4.1.37950.1.1.6.2.2.1.1.9
		-- 1.3.6.1.4.1.37950.1.1.6.2.2.1.1.9
		onuPMaxIpv6hostShow OBJECT-TYPE
			SYNTAX Integer32
			MAX-ACCESS read-only
			STATUS current
			DESCRIPTION
				"Description."
			::= { v1600gOnuPEntry 9 }

		
--  1.3.6.1.4.1.37950.1.1.6.2.2.1.1.10
		-- 1.3.6.1.4.1.37950.1.1.6.2.2.1.1.10
		onuPMaxVeipShow OBJECT-TYPE
			SYNTAX Integer32
			MAX-ACCESS read-only
			STATUS current
			DESCRIPTION
				"Description."
			::= { v1600gOnuPEntry 10 }

		
--  1.3.6.1.4.1.37950.1.1.6.2.2.1.1.11
		-- 1.3.6.1.4.1.37950.1.1.6.2.2.1.1.11
		onuPSrvN1Show OBJECT-TYPE
			SYNTAX Integer32
			MAX-ACCESS read-only
			STATUS current
			DESCRIPTION
				"Description."
			::= { v1600gOnuPEntry 11 }

		
--  1.3.6.1.4.1.37950.1.1.6.2.2.1.1.12
		-- 1.3.6.1.4.1.37950.1.1.6.2.2.1.1.12
		onuPSrv1MShow OBJECT-TYPE
			SYNTAX Integer32
			MAX-ACCESS read-only
			STATUS current
			DESCRIPTION
				"Description."
			::= { v1600gOnuPEntry 12 }

		
--  1.3.6.1.4.1.37950.1.1.6.2.2.1.1.13
		-- 1.3.6.1.4.1.37950.1.1.6.2.2.1.1.13
		onuPSrv1PShow OBJECT-TYPE
			SYNTAX Integer32
			MAX-ACCESS read-only
			STATUS current
			DESCRIPTION
				"Description."
			::= { v1600gOnuPEntry 13 }

		
--  1.3.6.1.4.1.37950.1.1.6.2.2.1.1.14
		-- 1.3.6.1.4.1.37950.1.1.6.2.2.1.1.14
		onuPWMNOmciShow OBJECT-TYPE
			SYNTAX Integer32
			MAX-ACCESS read-only
			STATUS current
			DESCRIPTION
				"Description."
			::= { v1600gOnuPEntry 14 }

		
--  1.3.6.1.4.1.37950.1.1.6.2.2.1.1.15
		-- 1.3.6.1.4.1.37950.1.1.6.2.2.1.1.15
		onuPOmciSendModeShow OBJECT-TYPE
			SYNTAX Integer32
			MAX-ACCESS read-only
			STATUS current
			DESCRIPTION
				"Description."
			::= { v1600gOnuPEntry 15 }

		
--  1.3.6.1.4.1.37950.1.1.6.2.2.1.1.16
		-- 1.3.6.1.4.1.37950.1.1.6.2.2.1.1.16
		onuPDMRangeShow OBJECT-TYPE
			SYNTAX Integer32
			MAX-ACCESS read-only
			STATUS current
			DESCRIPTION
				"Description."
			::= { v1600gOnuPEntry 16 }

		
--  1.3.6.1.4.1.37950.1.1.6.2.2.1.1.17
		-- 1.3.6.1.4.1.37950.1.1.6.2.2.1.1.17
		v1600gOnuPSrvAbility OBJECT-TYPE
			SYNTAX INTEGER
				{
				support(0),
				not-support(1)
				}
			MAX-ACCESS read-only
			STATUS current
			DESCRIPTION
				"Description."
			::= { v1600gOnuPEntry 17 }

		
--  1.3.6.1.4.1.37950.1.1.6.2.2.2
		-- 1.3.6.1.4.1.37950.1.1.6.2.2.2
		v1600gDbaPTable OBJECT-TYPE
			SYNTAX SEQUENCE OF V1600gDbaPEntry
			MAX-ACCESS not-accessible
			STATUS current
			DESCRIPTION
				"Description."
			::= { v1600gProfileShow 2 }

		
--  1.3.6.1.4.1.37950.1.1.6.2.2.2.1
		-- 1.3.6.1.4.1.37950.1.1.6.2.2.2.1
		v1600gDbaPEntry OBJECT-TYPE
			SYNTAX V1600gDbaPEntry
			MAX-ACCESS not-accessible
			STATUS current
			DESCRIPTION
				"Description."
			INDEX { dbaPIdShow }
			::= { v1600gDbaPTable 1 }

		
		V1600gDbaPEntry ::=
			SEQUENCE { 
				dbaPIdShow
					Integer32,
				dbaPNameShow
					OCTET STRING,
				dbaPTypeShow
					Integer32,
				dbaPFixedShow
					Integer32,
				dbaPAssuredShow
					Integer32,
				dbaPMaximumShow
					Integer32
			 }

--  1.3.6.1.4.1.37950.1.1.6.2.2.2.1.1
		-- 1.3.6.1.4.1.37950.1.1.6.2.2.2.1.1
		dbaPIdShow OBJECT-TYPE
			SYNTAX Integer32
			MAX-ACCESS read-only
			STATUS current
			DESCRIPTION
				"Description."
			::= { v1600gDbaPEntry 1 }

		
--  1.3.6.1.4.1.37950.1.1.6.2.2.2.1.2
		-- 1.3.6.1.4.1.37950.1.1.6.2.2.2.1.2
		dbaPNameShow OBJECT-TYPE
			SYNTAX OCTET STRING
			MAX-ACCESS read-only
			STATUS current
			DESCRIPTION
				"Description."
			::= { v1600gDbaPEntry 2 }

		
--  1.3.6.1.4.1.37950.1.1.6.2.2.2.1.3
		-- 1.3.6.1.4.1.37950.1.1.6.2.2.2.1.3
		dbaPTypeShow OBJECT-TYPE
			SYNTAX Integer32
			MAX-ACCESS read-only
			STATUS current
			DESCRIPTION
				"Description."
			::= { v1600gDbaPEntry 3 }

		
--  1.3.6.1.4.1.37950.1.1.6.2.2.2.1.4
		-- 1.3.6.1.4.1.37950.1.1.6.2.2.2.1.4
		dbaPFixedShow OBJECT-TYPE
			SYNTAX Integer32
			MAX-ACCESS read-only
			STATUS current
			DESCRIPTION
				"Description."
			::= { v1600gDbaPEntry 4 }

		
--  1.3.6.1.4.1.37950.1.1.6.2.2.2.1.5
		-- 1.3.6.1.4.1.37950.1.1.6.2.2.2.1.5
		dbaPAssuredShow OBJECT-TYPE
			SYNTAX Integer32
			MAX-ACCESS read-only
			STATUS current
			DESCRIPTION
				"Description."
			::= { v1600gDbaPEntry 5 }

		
--  1.3.6.1.4.1.37950.1.1.6.2.2.2.1.6
		-- 1.3.6.1.4.1.37950.1.1.6.2.2.2.1.6
		dbaPMaximumShow OBJECT-TYPE
			SYNTAX Integer32
			MAX-ACCESS read-only
			STATUS current
			DESCRIPTION
				"Description."
			::= { v1600gDbaPEntry 6 }

		
--  1.3.6.1.4.1.37950.1.1.6.2.2.3
		-- 1.3.6.1.4.1.37950.1.1.6.2.2.3
		v1600gTrafficPTable OBJECT-TYPE
			SYNTAX SEQUENCE OF V1600gTrafficPEntry
			MAX-ACCESS not-accessible
			STATUS current
			DESCRIPTION
				"Description."
			::= { v1600gProfileShow 3 }

		
--  1.3.6.1.4.1.37950.1.1.6.2.2.3.1
		-- 1.3.6.1.4.1.37950.1.1.6.2.2.3.1
		v1600gTrafficPEntry OBJECT-TYPE
			SYNTAX V1600gTrafficPEntry
			MAX-ACCESS not-accessible
			STATUS current
			DESCRIPTION
				"Description."
			INDEX { trafficPidShow }
			::= { v1600gTrafficPTable 1 }

		
		V1600gTrafficPEntry ::=
			SEQUENCE { 
				trafficPidShow
					Integer32,
				trafficPNameShow
					OCTET STRING,
				trafficPSirShow
					Integer32,
				trafficPPirShow
					Integer32,
				trafficPCbsShow
					Integer32,
				trafficPPbsShow
					Integer32
			 }

--  1.3.6.1.4.1.37950.1.1.6.2.2.3.1.1
		-- 1.3.6.1.4.1.37950.1.1.6.2.2.3.1.1
		trafficPidShow OBJECT-TYPE
			SYNTAX Integer32
			MAX-ACCESS read-only
			STATUS current
			DESCRIPTION
				"Description."
			::= { v1600gTrafficPEntry 1 }

		
--  1.3.6.1.4.1.37950.1.1.6.2.2.3.1.2
		-- 1.3.6.1.4.1.37950.1.1.6.2.2.3.1.2
		trafficPNameShow OBJECT-TYPE
			SYNTAX OCTET STRING
			MAX-ACCESS read-only
			STATUS current
			DESCRIPTION
				"Description."
			::= { v1600gTrafficPEntry 2 }

		
--  1.3.6.1.4.1.37950.1.1.6.2.2.3.1.3
		-- 1.3.6.1.4.1.37950.1.1.6.2.2.3.1.3
		trafficPSirShow OBJECT-TYPE
			SYNTAX Integer32
			MAX-ACCESS read-only
			STATUS current
			DESCRIPTION
				"Description."
			::= { v1600gTrafficPEntry 3 }

		
--  1.3.6.1.4.1.37950.1.1.6.2.2.3.1.4
		-- 1.3.6.1.4.1.37950.1.1.6.2.2.3.1.4
		trafficPPirShow OBJECT-TYPE
			SYNTAX Integer32
			MAX-ACCESS read-only
			STATUS current
			DESCRIPTION
				"Description."
			::= { v1600gTrafficPEntry 4 }

		
--  1.3.6.1.4.1.37950.1.1.6.2.2.3.1.5
		-- 1.3.6.1.4.1.37950.1.1.6.2.2.3.1.5
		trafficPCbsShow OBJECT-TYPE
			SYNTAX Integer32
			MAX-ACCESS read-only
			STATUS current
			DESCRIPTION
				"Description."
			::= { v1600gTrafficPEntry 5 }

		
--  1.3.6.1.4.1.37950.1.1.6.2.2.3.1.6
		-- 1.3.6.1.4.1.37950.1.1.6.2.2.3.1.6
		trafficPPbsShow OBJECT-TYPE
			SYNTAX Integer32
			MAX-ACCESS read-only
			STATUS current
			DESCRIPTION
				"Description."
			::= { v1600gTrafficPEntry 6 }

		
--  1.3.6.1.4.1.37950.1.1.6.2.2.4
		-- 1.3.6.1.4.1.37950.1.1.6.2.2.4
		v1600gLinePShow OBJECT IDENTIFIER ::= { v1600gProfileShow 4 }

		
--  1.3.6.1.4.1.37950.1.1.6.2.2.4.1
		-- 1.3.6.1.4.1.37950.1.1.6.2.2.4.1
		linePNameTable OBJECT-TYPE
			SYNTAX SEQUENCE OF LinePNameEntry
			MAX-ACCESS not-accessible
			STATUS current
			DESCRIPTION
				"Description."
			::= { v1600gLinePShow 1 }

		
--  1.3.6.1.4.1.37950.1.1.6.2.2.4.1.1
		-- 1.3.6.1.4.1.37950.1.1.6.2.2.4.1.1
		linePNameEntry OBJECT-TYPE
			SYNTAX LinePNameEntry
			MAX-ACCESS not-accessible
			STATUS current
			DESCRIPTION
				"Description."
			INDEX { linePNamePId }
			::= { linePNameTable 1 }

		
		LinePNameEntry ::=
			SEQUENCE { 
				linePNamePId
					Integer32,
				linePNameTableName
					OCTET STRING
			 }

--  1.3.6.1.4.1.37950.1.1.6.2.2.4.1.1.1
		-- 1.3.6.1.4.1.37950.1.1.6.2.2.4.1.1.1
		linePNamePId OBJECT-TYPE
			SYNTAX Integer32
			MAX-ACCESS read-only
			STATUS current
			DESCRIPTION
				"Description."
			::= { linePNameEntry 1 }

		
--  1.3.6.1.4.1.37950.1.1.6.2.2.4.1.1.2
		-- 1.3.6.1.4.1.37950.1.1.6.2.2.4.1.1.2
		linePNameTableName OBJECT-TYPE
			SYNTAX OCTET STRING
			MAX-ACCESS read-only
			STATUS current
			DESCRIPTION
				"Description."
			::= { linePNameEntry 2 }

		
--  1.3.6.1.4.1.37950.1.1.6.2.2.4.2
		-- 1.3.6.1.4.1.37950.1.1.6.2.2.4.2
		linePTcontTable OBJECT-TYPE
			SYNTAX SEQUENCE OF LinePTcontEntry
			MAX-ACCESS not-accessible
			STATUS current
			DESCRIPTION
				"Description."
			::= { v1600gLinePShow 2 }

		
--  1.3.6.1.4.1.37950.1.1.6.2.2.4.2.1
		-- 1.3.6.1.4.1.37950.1.1.6.2.2.4.2.1
		linePTcontEntry OBJECT-TYPE
			SYNTAX LinePTcontEntry
			MAX-ACCESS not-accessible
			STATUS current
			DESCRIPTION
				"Description."
			INDEX { linePTcontPId, linePTcontTId }
			::= { linePTcontTable 1 }

		
		LinePTcontEntry ::=
			SEQUENCE { 
				linePTcontPId
					Integer32,
				linePTcontTId
					Integer32,
				linePTcontTName
					OCTET STRING,
				linePTcontTDbaName
					OCTET STRING
			 }

--  1.3.6.1.4.1.37950.1.1.6.2.2.4.2.1.1
		-- 1.3.6.1.4.1.37950.1.1.6.2.2.4.2.1.1
		linePTcontPId OBJECT-TYPE
			SYNTAX Integer32
			MAX-ACCESS read-only
			STATUS current
			DESCRIPTION
				"Description."
			::= { linePTcontEntry 1 }

		
--  1.3.6.1.4.1.37950.1.1.6.2.2.4.2.1.2
		-- 1.3.6.1.4.1.37950.1.1.6.2.2.4.2.1.2
		linePTcontTId OBJECT-TYPE
			SYNTAX Integer32
			MAX-ACCESS read-only
			STATUS current
			DESCRIPTION
				"Description."
			::= { linePTcontEntry 2 }

		
--  1.3.6.1.4.1.37950.1.1.6.2.2.4.2.1.3
		-- 1.3.6.1.4.1.37950.1.1.6.2.2.4.2.1.3
		linePTcontTName OBJECT-TYPE
			SYNTAX OCTET STRING
			MAX-ACCESS read-only
			STATUS current
			DESCRIPTION
				"Description."
			::= { linePTcontEntry 3 }

		
--  1.3.6.1.4.1.37950.1.1.6.2.2.4.2.1.4
		-- 1.3.6.1.4.1.37950.1.1.6.2.2.4.2.1.4
		linePTcontTDbaName OBJECT-TYPE
			SYNTAX OCTET STRING
			MAX-ACCESS read-only
			STATUS current
			DESCRIPTION
				"Description."
			::= { linePTcontEntry 4 }

		
--  1.3.6.1.4.1.37950.1.1.6.2.2.4.3
		-- 1.3.6.1.4.1.37950.1.1.6.2.2.4.3
		linePGemTable OBJECT-TYPE
			SYNTAX SEQUENCE OF LinePGemEntry
			MAX-ACCESS not-accessible
			STATUS current
			DESCRIPTION
				"Description."
			::= { v1600gLinePShow 3 }

		
--  1.3.6.1.4.1.37950.1.1.6.2.2.4.3.1
		-- 1.3.6.1.4.1.37950.1.1.6.2.2.4.3.1
		linePGemEntry OBJECT-TYPE
			SYNTAX LinePGemEntry
			MAX-ACCESS not-accessible
			STATUS current
			DESCRIPTION
				"Description."
			INDEX { linePGemPId, linePGemGId, linePGemGTcontId }
			::= { linePGemTable 1 }

		
		LinePGemEntry ::=
			SEQUENCE { 
				linePGemPId
					Integer32,
				linePGemGId
					Integer32,
				linePGemGName
					OCTET STRING,
				linePGemGTcontId
					Integer32,
				linePGemGCos
					Integer32,
				linePGemGUpTraffic
					OCTET STRING,
				linePGemGDnTraffic
					OCTET STRING,
				linePGemGUpQId
					Integer32,
				linePGemGDnQId
					Integer32,
				linePGemGState
					Integer32
			 }

--  1.3.6.1.4.1.37950.1.1.6.2.2.4.3.1.1
		-- 1.3.6.1.4.1.37950.1.1.6.2.2.4.3.1.1
		linePGemPId OBJECT-TYPE
			SYNTAX Integer32
			MAX-ACCESS read-only
			STATUS current
			DESCRIPTION
				"Description."
			::= { linePGemEntry 1 }

		
--  1.3.6.1.4.1.37950.1.1.6.2.2.4.3.1.2
		-- 1.3.6.1.4.1.37950.1.1.6.2.2.4.3.1.2
		linePGemGId OBJECT-TYPE
			SYNTAX Integer32
			MAX-ACCESS read-only
			STATUS current
			DESCRIPTION
				"Description."
			::= { linePGemEntry 2 }

		
--  1.3.6.1.4.1.37950.1.1.6.2.2.4.3.1.3
		-- 1.3.6.1.4.1.37950.1.1.6.2.2.4.3.1.3
		linePGemGName OBJECT-TYPE
			SYNTAX OCTET STRING
			MAX-ACCESS read-only
			STATUS current
			DESCRIPTION
				"Description."
			::= { linePGemEntry 3 }

		
--  1.3.6.1.4.1.37950.1.1.6.2.2.4.3.1.4
		-- 1.3.6.1.4.1.37950.1.1.6.2.2.4.3.1.4
		linePGemGTcontId OBJECT-TYPE
			SYNTAX Integer32
			MAX-ACCESS read-only
			STATUS current
			DESCRIPTION
				"Description."
			::= { linePGemEntry 4 }

		
--  1.3.6.1.4.1.37950.1.1.6.2.2.4.3.1.5
		-- 1.3.6.1.4.1.37950.1.1.6.2.2.4.3.1.5
		linePGemGCos OBJECT-TYPE
			SYNTAX Integer32
			MAX-ACCESS read-only
			STATUS current
			DESCRIPTION
				"Description."
			::= { linePGemEntry 5 }

		
--  1.3.6.1.4.1.37950.1.1.6.2.2.4.3.1.6
		-- 1.3.6.1.4.1.37950.1.1.6.2.2.4.3.1.6
		linePGemGUpTraffic OBJECT-TYPE
			SYNTAX OCTET STRING
			MAX-ACCESS read-only
			STATUS current
			DESCRIPTION
				"Description."
			::= { linePGemEntry 6 }

		
--  1.3.6.1.4.1.37950.1.1.6.2.2.4.3.1.7
		-- 1.3.6.1.4.1.37950.1.1.6.2.2.4.3.1.7
		linePGemGDnTraffic OBJECT-TYPE
			SYNTAX OCTET STRING
			MAX-ACCESS read-only
			STATUS current
			DESCRIPTION
				"Description."
			::= { linePGemEntry 7 }

		
--  1.3.6.1.4.1.37950.1.1.6.2.2.4.3.1.8
		-- 1.3.6.1.4.1.37950.1.1.6.2.2.4.3.1.8
		linePGemGUpQId OBJECT-TYPE
			SYNTAX Integer32
			MAX-ACCESS read-only
			STATUS current
			DESCRIPTION
				"Description."
			::= { linePGemEntry 8 }

		
--  1.3.6.1.4.1.37950.1.1.6.2.2.4.3.1.9
		-- 1.3.6.1.4.1.37950.1.1.6.2.2.4.3.1.9
		linePGemGDnQId OBJECT-TYPE
			SYNTAX Integer32
			MAX-ACCESS read-only
			STATUS current
			DESCRIPTION
				"Description."
			::= { linePGemEntry 9 }

		
--  1.3.6.1.4.1.37950.1.1.6.2.2.4.3.1.10
		-- 1.3.6.1.4.1.37950.1.1.6.2.2.4.3.1.10
		linePGemGState OBJECT-TYPE
			SYNTAX Integer32
			MAX-ACCESS read-only
			STATUS current
			DESCRIPTION
				"Description."
			::= { linePGemEntry 10 }

		
--  1.3.6.1.4.1.37950.1.1.6.2.2.4.4
		-- 1.3.6.1.4.1.37950.1.1.6.2.2.4.4
		linePSrvTable OBJECT-TYPE
			SYNTAX SEQUENCE OF LinePSrvEntry
			MAX-ACCESS not-accessible
			STATUS current
			DESCRIPTION
				"Description."
			::= { v1600gLinePShow 4 }

		
--  1.3.6.1.4.1.37950.1.1.6.2.2.4.4.1
		-- 1.3.6.1.4.1.37950.1.1.6.2.2.4.4.1
		linePSrvEntry OBJECT-TYPE
			SYNTAX LinePSrvEntry
			MAX-ACCESS not-accessible
			STATUS current
			DESCRIPTION
				"Description."
			INDEX { linePSrvPId, linePSrvSName }
			::= { linePSrvTable 1 }

		
		LinePSrvEntry ::=
			SEQUENCE { 
				linePSrvPId
					Integer32,
				linePSrvSName
					OCTET STRING,
				linePSrvSGemId
					Integer32,
				linePSrvSVlanMode
					INTEGER,
				linePSrvSVlanList
					OCTET STRING,
				linePSrvSCosList
					OCTET STRING,
				linePSrvSPortType
					INTEGER,
				linePSrvSEthuni
					Integer32,
				linePSrvSIphost
					Integer32
			 }

--  1.3.6.1.4.1.37950.1.1.6.2.2.4.4.1.1
		-- 1.3.6.1.4.1.37950.1.1.6.2.2.4.4.1.1
		linePSrvPId OBJECT-TYPE
			SYNTAX Integer32
			MAX-ACCESS read-only
			STATUS current
			DESCRIPTION
				"Description."
			::= { linePSrvEntry 1 }

		
--  1.3.6.1.4.1.37950.1.1.6.2.2.4.4.1.2
		-- 1.3.6.1.4.1.37950.1.1.6.2.2.4.4.1.2
		linePSrvSName OBJECT-TYPE
			SYNTAX OCTET STRING
			MAX-ACCESS read-only
			STATUS current
			DESCRIPTION
				"Description."
			::= { linePSrvEntry 2 }

		
--  1.3.6.1.4.1.37950.1.1.6.2.2.4.4.1.3
		-- 1.3.6.1.4.1.37950.1.1.6.2.2.4.4.1.3
		linePSrvSGemId OBJECT-TYPE
			SYNTAX Integer32
			MAX-ACCESS read-only
			STATUS current
			DESCRIPTION
				"Description."
			::= { linePSrvEntry 3 }

		
--  1.3.6.1.4.1.37950.1.1.6.2.2.4.4.1.4
		-- 1.3.6.1.4.1.37950.1.1.6.2.2.4.4.1.4
		linePSrvSVlanMode OBJECT-TYPE
			SYNTAX INTEGER
				{
				tag(1),
				untag(2)
				}
			MAX-ACCESS read-only
			STATUS current
			DESCRIPTION
				"Description."
			::= { linePSrvEntry 4 }

		
--  1.3.6.1.4.1.37950.1.1.6.2.2.4.4.1.5
		-- 1.3.6.1.4.1.37950.1.1.6.2.2.4.4.1.5
		linePSrvSVlanList OBJECT-TYPE
			SYNTAX OCTET STRING
			MAX-ACCESS read-only
			STATUS current
			DESCRIPTION
				"Description."
			::= { linePSrvEntry 5 }

		
--  1.3.6.1.4.1.37950.1.1.6.2.2.4.4.1.6
		-- 1.3.6.1.4.1.37950.1.1.6.2.2.4.4.1.6
		linePSrvSCosList OBJECT-TYPE
			SYNTAX OCTET STRING
			MAX-ACCESS read-write
			STATUS current
			DESCRIPTION
				"Description."
			::= { linePSrvEntry 6 }

		
--  1.3.6.1.4.1.37950.1.1.6.2.2.4.4.1.7
		-- 1.3.6.1.4.1.37950.1.1.6.2.2.4.4.1.7
		linePSrvSPortType OBJECT-TYPE
			SYNTAX INTEGER
				{
				null(0),
				eth(1),
				iphost(2)
				}
			MAX-ACCESS read-write
			STATUS current
			DESCRIPTION
				"Description."
			::= { linePSrvEntry 7 }

		
--  1.3.6.1.4.1.37950.1.1.6.2.2.4.4.1.8
		-- 1.3.6.1.4.1.37950.1.1.6.2.2.4.4.1.8
		linePSrvSEthuni OBJECT-TYPE
			SYNTAX Integer32
			MAX-ACCESS read-write
			STATUS current
			DESCRIPTION
				"Description."
			::= { linePSrvEntry 8 }

		
--  1.3.6.1.4.1.37950.1.1.6.2.2.4.4.1.9
		-- 1.3.6.1.4.1.37950.1.1.6.2.2.4.4.1.9
		linePSrvSIphost OBJECT-TYPE
			SYNTAX Integer32
			MAX-ACCESS read-write
			STATUS current
			DESCRIPTION
				"Description."
			::= { linePSrvEntry 9 }

		
--  1.3.6.1.4.1.37950.1.1.6.2.2.4.5
		-- 1.3.6.1.4.1.37950.1.1.6.2.2.4.5
		linePSrvPortTable OBJECT-TYPE
			SYNTAX SEQUENCE OF LinePSrvPortEntry
			MAX-ACCESS not-accessible
			STATUS current
			DESCRIPTION
				"Description."
			::= { v1600gLinePShow 5 }

		
--  1.3.6.1.4.1.37950.1.1.6.2.2.4.5.1
		-- 1.3.6.1.4.1.37950.1.1.6.2.2.4.5.1
		linePSrvPortEntry OBJECT-TYPE
			SYNTAX LinePSrvPortEntry
			MAX-ACCESS not-accessible
			STATUS current
			DESCRIPTION
				"Description."
			INDEX { linePSrvPortPId, linePSrvPortSPId }
			::= { linePSrvPortTable 1 }

		
		LinePSrvPortEntry ::=
			SEQUENCE { 
				linePSrvPortPId
					Integer32,
				linePSrvPortSPId
					Integer32,
				linePSrvPortSPGemId
					Integer32,
				linePSrvPortSPBVid
					Integer32,
				linePSrvPortSPEVid
					Integer32,
				linePSrvPortSPOVid
					Integer32,
				linePSrvPortSPIVid
					Integer32,
				linePSrvPortSPUPri
					Integer32,
				linePSrvPortSPEType
					OCTET STRING,
				linePSrvPortSPVid
					Integer32,
				linePSrvPortSPCos
					Integer32,
				linePSrvPortSPSVid
					Integer32,
				linePSrvPortSPSCos
					Integer32,
				linePSrvPortSPMode
					Integer32,
				linePSrvPortSPState
					Integer32,
				linePSrvPortSPDesc
					OCTET STRING
			 }

--  1.3.6.1.4.1.37950.1.1.6.2.2.4.5.1.1
		-- 1.3.6.1.4.1.37950.1.1.6.2.2.4.5.1.1
		linePSrvPortPId OBJECT-TYPE
			SYNTAX Integer32
			MAX-ACCESS read-only
			STATUS current
			DESCRIPTION
				"Description."
			::= { linePSrvPortEntry 1 }

		
--  1.3.6.1.4.1.37950.1.1.6.2.2.4.5.1.2
		-- 1.3.6.1.4.1.37950.1.1.6.2.2.4.5.1.2
		linePSrvPortSPId OBJECT-TYPE
			SYNTAX Integer32
			MAX-ACCESS read-only
			STATUS current
			DESCRIPTION
				"Description."
			::= { linePSrvPortEntry 2 }

		
--  1.3.6.1.4.1.37950.1.1.6.2.2.4.5.1.3
		-- 1.3.6.1.4.1.37950.1.1.6.2.2.4.5.1.3
		linePSrvPortSPGemId OBJECT-TYPE
			SYNTAX Integer32
			MAX-ACCESS read-only
			STATUS current
			DESCRIPTION
				"Description."
			::= { linePSrvPortEntry 3 }

		
--  1.3.6.1.4.1.37950.1.1.6.2.2.4.5.1.4
		-- 1.3.6.1.4.1.37950.1.1.6.2.2.4.5.1.4
		linePSrvPortSPBVid OBJECT-TYPE
			SYNTAX Integer32
			MAX-ACCESS read-only
			STATUS current
			DESCRIPTION
				"Description."
			::= { linePSrvPortEntry 4 }

		
--  1.3.6.1.4.1.37950.1.1.6.2.2.4.5.1.5
		-- 1.3.6.1.4.1.37950.1.1.6.2.2.4.5.1.5
		linePSrvPortSPEVid OBJECT-TYPE
			SYNTAX Integer32
			MAX-ACCESS read-only
			STATUS current
			DESCRIPTION
				"Description."
			::= { linePSrvPortEntry 5 }

		
--  1.3.6.1.4.1.37950.1.1.6.2.2.4.5.1.6
		-- 1.3.6.1.4.1.37950.1.1.6.2.2.4.5.1.6
		linePSrvPortSPOVid OBJECT-TYPE
			SYNTAX Integer32
			MAX-ACCESS read-only
			STATUS current
			DESCRIPTION
				"Description."
			::= { linePSrvPortEntry 6 }

		
--  1.3.6.1.4.1.37950.1.1.6.2.2.4.5.1.7
		-- 1.3.6.1.4.1.37950.1.1.6.2.2.4.5.1.7
		linePSrvPortSPIVid OBJECT-TYPE
			SYNTAX Integer32
			MAX-ACCESS read-only
			STATUS current
			DESCRIPTION
				"Description."
			::= { linePSrvPortEntry 7 }

		
--  1.3.6.1.4.1.37950.1.1.6.2.2.4.5.1.8
		-- 1.3.6.1.4.1.37950.1.1.6.2.2.4.5.1.8
		linePSrvPortSPUPri OBJECT-TYPE
			SYNTAX Integer32
			MAX-ACCESS read-only
			STATUS current
			DESCRIPTION
				"Description."
			::= { linePSrvPortEntry 8 }

		
--  1.3.6.1.4.1.37950.1.1.6.2.2.4.5.1.9
		-- 1.3.6.1.4.1.37950.1.1.6.2.2.4.5.1.9
		linePSrvPortSPEType OBJECT-TYPE
			SYNTAX OCTET STRING
			MAX-ACCESS read-only
			STATUS current
			DESCRIPTION
				"Description."
			::= { linePSrvPortEntry 9 }

		
--  1.3.6.1.4.1.37950.1.1.6.2.2.4.5.1.10
		-- 1.3.6.1.4.1.37950.1.1.6.2.2.4.5.1.10
		linePSrvPortSPVid OBJECT-TYPE
			SYNTAX Integer32
			MAX-ACCESS read-only
			STATUS current
			DESCRIPTION
				"Description."
			::= { linePSrvPortEntry 10 }

		
--  1.3.6.1.4.1.37950.1.1.6.2.2.4.5.1.11
		-- 1.3.6.1.4.1.37950.1.1.6.2.2.4.5.1.11
		linePSrvPortSPCos OBJECT-TYPE
			SYNTAX Integer32
			MAX-ACCESS read-only
			STATUS current
			DESCRIPTION
				"Description."
			::= { linePSrvPortEntry 11 }

		
--  1.3.6.1.4.1.37950.1.1.6.2.2.4.5.1.12
		-- 1.3.6.1.4.1.37950.1.1.6.2.2.4.5.1.12
		linePSrvPortSPSVid OBJECT-TYPE
			SYNTAX Integer32
			MAX-ACCESS read-only
			STATUS current
			DESCRIPTION
				"Description."
			::= { linePSrvPortEntry 12 }

		
--  1.3.6.1.4.1.37950.1.1.6.2.2.4.5.1.13
		-- 1.3.6.1.4.1.37950.1.1.6.2.2.4.5.1.13
		linePSrvPortSPSCos OBJECT-TYPE
			SYNTAX Integer32
			MAX-ACCESS read-only
			STATUS current
			DESCRIPTION
				"Description."
			::= { linePSrvPortEntry 13 }

		
--  1.3.6.1.4.1.37950.1.1.6.2.2.4.5.1.14
		-- 1.3.6.1.4.1.37950.1.1.6.2.2.4.5.1.14
		linePSrvPortSPMode OBJECT-TYPE
			SYNTAX Integer32
			MAX-ACCESS read-only
			STATUS current
			DESCRIPTION
				"Description."
			::= { linePSrvPortEntry 14 }

		
--  1.3.6.1.4.1.37950.1.1.6.2.2.4.5.1.15
		-- 1.3.6.1.4.1.37950.1.1.6.2.2.4.5.1.15
		linePSrvPortSPState OBJECT-TYPE
			SYNTAX Integer32
			MAX-ACCESS read-only
			STATUS current
			DESCRIPTION
				"Description."
			::= { linePSrvPortEntry 15 }

		
--  1.3.6.1.4.1.37950.1.1.6.2.2.4.5.1.16
		-- 1.3.6.1.4.1.37950.1.1.6.2.2.4.5.1.16
		linePSrvPortSPDesc OBJECT-TYPE
			SYNTAX OCTET STRING
			MAX-ACCESS read-only
			STATUS current
			DESCRIPTION
				"Description."
			::= { linePSrvPortEntry 16 }

		
--  1.3.6.1.4.1.37950.1.1.6.2.2.4.6
		-- 1.3.6.1.4.1.37950.1.1.6.2.2.4.6
		linePMVlanTable OBJECT-TYPE
			SYNTAX SEQUENCE OF LinePMVlanEntry
			MAX-ACCESS not-accessible
			STATUS current
			DESCRIPTION
				"Description."
			::= { v1600gLinePShow 6 }

		
--  1.3.6.1.4.1.37950.1.1.6.2.2.4.6.1
		-- 1.3.6.1.4.1.37950.1.1.6.2.2.4.6.1
		linePMVlanEntry OBJECT-TYPE
			SYNTAX LinePMVlanEntry
			MAX-ACCESS not-accessible
			STATUS current
			DESCRIPTION
				"Description."
			INDEX { linePMVlanPid }
			::= { linePMVlanTable 1 }

		
		LinePMVlanEntry ::=
			SEQUENCE { 
				linePMVlanPid
					Integer32,
				linePMVVlanList
					OCTET STRING
			 }

--  1.3.6.1.4.1.37950.1.1.6.2.2.4.6.1.1
		-- 1.3.6.1.4.1.37950.1.1.6.2.2.4.6.1.1
		linePMVlanPid OBJECT-TYPE
			SYNTAX Integer32
			MAX-ACCESS read-only
			STATUS current
			DESCRIPTION
				"Description."
			::= { linePMVlanEntry 1 }

		
--  1.3.6.1.4.1.37950.1.1.6.2.2.4.6.1.2
		-- 1.3.6.1.4.1.37950.1.1.6.2.2.4.6.1.2
		linePMVVlanList OBJECT-TYPE
			SYNTAX OCTET STRING
			MAX-ACCESS read-only
			STATUS current
			DESCRIPTION
				"Description."
			::= { linePMVlanEntry 2 }

		
--  1.3.6.1.4.1.37950.1.1.6.2.2.5
		-- 1.3.6.1.4.1.37950.1.1.6.2.2.5
		v1600gSrvPShow OBJECT IDENTIFIER ::= { v1600gProfileShow 5 }

		
--  1.3.6.1.4.1.37950.1.1.6.2.2.5.1
		-- 1.3.6.1.4.1.37950.1.1.6.2.2.5.1
		srvPNameTable OBJECT-TYPE
			SYNTAX SEQUENCE OF SrvPNameEntry
			MAX-ACCESS not-accessible
			STATUS current
			DESCRIPTION
				"Description."
			::= { v1600gSrvPShow 1 }

		
--  1.3.6.1.4.1.37950.1.1.6.2.2.5.1.1
		-- 1.3.6.1.4.1.37950.1.1.6.2.2.5.1.1
		srvPNameEntry OBJECT-TYPE
			SYNTAX SrvPNameEntry
			MAX-ACCESS not-accessible
			STATUS current
			DESCRIPTION
				"Description."
			INDEX { srvPNamePId }
			::= { srvPNameTable 1 }

		
		SrvPNameEntry ::=
			SEQUENCE { 
				srvPNamePId
					Integer32,
				srvPNameTableName
					OCTET STRING
			 }

--  1.3.6.1.4.1.37950.1.1.6.2.2.5.1.1.1
		-- 1.3.6.1.4.1.37950.1.1.6.2.2.5.1.1.1
		srvPNamePId OBJECT-TYPE
			SYNTAX Integer32
			MAX-ACCESS read-only
			STATUS current
			DESCRIPTION
				"Description."
			::= { srvPNameEntry 1 }

		
--  1.3.6.1.4.1.37950.1.1.6.2.2.5.1.1.2
		-- 1.3.6.1.4.1.37950.1.1.6.2.2.5.1.1.2
		srvPNameTableName OBJECT-TYPE
			SYNTAX OCTET STRING
			MAX-ACCESS read-only
			STATUS current
			DESCRIPTION
				"Description."
			::= { srvPNameEntry 2 }

		
--  1.3.6.1.4.1.37950.1.1.6.2.2.5.2
		-- 1.3.6.1.4.1.37950.1.1.6.2.2.5.2
		srvPPortVlanTable OBJECT-TYPE
			SYNTAX SEQUENCE OF SrvPPortVlanEntry
			MAX-ACCESS not-accessible
			STATUS current
			DESCRIPTION
				"Description."
			::= { v1600gSrvPShow 2 }

		
--  1.3.6.1.4.1.37950.1.1.6.2.2.5.2.1
		-- 1.3.6.1.4.1.37950.1.1.6.2.2.5.2.1
		srvPPortVlanEntry OBJECT-TYPE
			SYNTAX SrvPPortVlanEntry
			MAX-ACCESS not-accessible
			STATUS current
			DESCRIPTION
				"Description."
			INDEX { srvPPortVlanPId, srvPPortVlanPortName }
			::= { srvPPortVlanTable 1 }

		
		SrvPPortVlanEntry ::=
			SEQUENCE { 
				srvPPortVlanPId
					Integer32,
				srvPPortVlanPortName
					OCTET STRING,
				srvPPortVlanPortMode
					INTEGER,
				srvPPortVlanVlanTbl
					Integer32,
				srvPPortVlanVlanListTbl
					OCTET STRING,
				srvPPortVlanTagPri
					Integer32,
				srvPPortVlanDVid
					Integer32,
				srvPPortVlanDPri
					Integer32,
				srvPPortVlanTslCVid
					Integer32,
				srvPPortVlanTslCPri
					Integer32,
				srvPPortVlanTslSVid
					Integer32,
				srvPPortVlanTslSPri
					Integer32
			 }

--  1.3.6.1.4.1.37950.1.1.6.2.2.5.2.1.1
		-- 1.3.6.1.4.1.37950.1.1.6.2.2.5.2.1.1
		srvPPortVlanPId OBJECT-TYPE
			SYNTAX Integer32
			MAX-ACCESS read-only
			STATUS current
			DESCRIPTION
				"Description."
			::= { srvPPortVlanEntry 1 }

		
--  1.3.6.1.4.1.37950.1.1.6.2.2.5.2.1.2
		-- 1.3.6.1.4.1.37950.1.1.6.2.2.5.2.1.2
		srvPPortVlanPortName OBJECT-TYPE
			SYNTAX OCTET STRING
			MAX-ACCESS read-only
			STATUS current
			DESCRIPTION
				"Description."
			::= { srvPPortVlanEntry 2 }

		
--  1.3.6.1.4.1.37950.1.1.6.2.2.5.2.1.3
		-- 1.3.6.1.4.1.37950.1.1.6.2.2.5.2.1.3
		srvPPortVlanPortMode OBJECT-TYPE
			SYNTAX INTEGER
				{
				transparent(1),
				trunk(2),
				tag(3),
				hybrid(4),
				translate(5)
				}
			MAX-ACCESS read-only
			STATUS current
			DESCRIPTION
				"Description."
			::= { srvPPortVlanEntry 3 }

		
--  1.3.6.1.4.1.37950.1.1.6.2.2.5.2.1.4
		-- 1.3.6.1.4.1.37950.1.1.6.2.2.5.2.1.4
		srvPPortVlanVlanTbl OBJECT-TYPE
			SYNTAX Integer32 (1..4094)
			MAX-ACCESS read-only
			STATUS current
			DESCRIPTION
				"Description."
			::= { srvPPortVlanEntry 4 }

		
--  1.3.6.1.4.1.37950.1.1.6.2.2.5.2.1.5
		-- 1.3.6.1.4.1.37950.1.1.6.2.2.5.2.1.5
		srvPPortVlanVlanListTbl OBJECT-TYPE
			SYNTAX OCTET STRING
			MAX-ACCESS read-only
			STATUS current
			DESCRIPTION
				"Description."
			::= { srvPPortVlanEntry 5 }

		
--  1.3.6.1.4.1.37950.1.1.6.2.2.5.2.1.6
		-- 1.3.6.1.4.1.37950.1.1.6.2.2.5.2.1.6
		srvPPortVlanTagPri OBJECT-TYPE
			SYNTAX Integer32
			MAX-ACCESS read-only
			STATUS current
			DESCRIPTION
				"Description."
			::= { srvPPortVlanEntry 6 }

		
--  1.3.6.1.4.1.37950.1.1.6.2.2.5.2.1.7
		-- 1.3.6.1.4.1.37950.1.1.6.2.2.5.2.1.7
		srvPPortVlanDVid OBJECT-TYPE
			SYNTAX Integer32
			MAX-ACCESS read-only
			STATUS current
			DESCRIPTION
				"Description."
			::= { srvPPortVlanEntry 7 }

		
--  1.3.6.1.4.1.37950.1.1.6.2.2.5.2.1.8
		-- 1.3.6.1.4.1.37950.1.1.6.2.2.5.2.1.8
		srvPPortVlanDPri OBJECT-TYPE
			SYNTAX Integer32
			MAX-ACCESS read-only
			STATUS current
			DESCRIPTION
				"Description."
			::= { srvPPortVlanEntry 8 }

		
--  1.3.6.1.4.1.37950.1.1.6.2.2.5.2.1.9
		-- 1.3.6.1.4.1.37950.1.1.6.2.2.5.2.1.9
		srvPPortVlanTslCVid OBJECT-TYPE
			SYNTAX Integer32
			MAX-ACCESS read-only
			STATUS current
			DESCRIPTION
				"Description."
			::= { srvPPortVlanEntry 9 }

		
--  1.3.6.1.4.1.37950.1.1.6.2.2.5.2.1.10
		-- 1.3.6.1.4.1.37950.1.1.6.2.2.5.2.1.10
		srvPPortVlanTslCPri OBJECT-TYPE
			SYNTAX Integer32
			MAX-ACCESS read-only
			STATUS current
			DESCRIPTION
				"Description."
			::= { srvPPortVlanEntry 10 }

		
--  1.3.6.1.4.1.37950.1.1.6.2.2.5.2.1.11
		-- 1.3.6.1.4.1.37950.1.1.6.2.2.5.2.1.11
		srvPPortVlanTslSVid OBJECT-TYPE
			SYNTAX Integer32
			MAX-ACCESS read-only
			STATUS current
			DESCRIPTION
				"Description."
			::= { srvPPortVlanEntry 11 }

		
--  1.3.6.1.4.1.37950.1.1.6.2.2.5.2.1.12
		-- 1.3.6.1.4.1.37950.1.1.6.2.2.5.2.1.12
		srvPPortVlanTslSPri OBJECT-TYPE
			SYNTAX Integer32
			MAX-ACCESS read-only
			STATUS current
			DESCRIPTION
				"Description."
			::= { srvPPortVlanEntry 12 }

		
--  1.3.6.1.4.1.37950.1.1.6.2.2.5.3
		-- 1.3.6.1.4.1.37950.1.1.6.2.2.5.3
		srvPMVlanStripTable OBJECT-TYPE
			SYNTAX SEQUENCE OF SrvPMVlanStripEntry
			MAX-ACCESS not-accessible
			STATUS current
			DESCRIPTION
				"Description."
			::= { v1600gSrvPShow 3 }

		
--  1.3.6.1.4.1.37950.1.1.6.2.2.5.3.1
		-- 1.3.6.1.4.1.37950.1.1.6.2.2.5.3.1
		srvPMVlanStripEntry OBJECT-TYPE
			SYNTAX SrvPMVlanStripEntry
			MAX-ACCESS not-accessible
			STATUS current
			DESCRIPTION
				"Description."
			INDEX { srvPMVlanStripPId, srvPMVStripPortId }
			::= { srvPMVlanStripTable 1 }

		
		SrvPMVlanStripEntry ::=
			SEQUENCE { 
				srvPMVlanStripPId
					Integer32,
				srvPMVStripPortId
					Integer32
			 }

--  1.3.6.1.4.1.37950.1.1.6.2.2.5.3.1.1
		-- 1.3.6.1.4.1.37950.1.1.6.2.2.5.3.1.1
		srvPMVlanStripPId OBJECT-TYPE
			SYNTAX Integer32
			MAX-ACCESS read-only
			STATUS current
			DESCRIPTION
				"Description."
			::= { srvPMVlanStripEntry 1 }

		
--  1.3.6.1.4.1.37950.1.1.6.2.2.5.3.1.2
		-- 1.3.6.1.4.1.37950.1.1.6.2.2.5.3.1.2
		srvPMVStripPortId OBJECT-TYPE
			SYNTAX Integer32
			MAX-ACCESS read-only
			STATUS current
			DESCRIPTION
				"Description."
			::= { srvPMVlanStripEntry 2 }

		
--  1.3.6.1.4.1.37950.1.1.6.2.2.5.4
		-- 1.3.6.1.4.1.37950.1.1.6.2.2.5.4
		srvPIphostTable OBJECT-TYPE
			SYNTAX SEQUENCE OF SrvPIphostEntry
			MAX-ACCESS not-accessible
			STATUS current
			DESCRIPTION
				"Description."
			::= { v1600gSrvPShow 4 }

		
--  1.3.6.1.4.1.37950.1.1.6.2.2.5.4.1
		-- 1.3.6.1.4.1.37950.1.1.6.2.2.5.4.1
		srvPIphostEntry OBJECT-TYPE
			SYNTAX SrvPIphostEntry
			MAX-ACCESS not-accessible
			STATUS current
			DESCRIPTION
				"Description."
			INDEX { srvPIphostPId, srvPIphostTId }
			::= { srvPIphostTable 1 }

		
		SrvPIphostEntry ::=
			SEQUENCE { 
				srvPIphostPId
					Integer32,
				srvPIphostTId
					Integer32,
				srvPIphostTDesc
					OCTET STRING,
				srvPIphostTMode
					INTEGER,
				srvPIphostTIpaddr
					IpAddress,
				srvPIphostTMask
					IpAddress,
				srvPIphostTGateway
					IpAddress,
				srvPIphostTPriDns
					IpAddress,
				srvPIphostTSecDns
					IpAddress,
				srvPIphostTVlan
					Integer32,
				srvPIphostTVlanPri
					Integer32
			 }

--  1.3.6.1.4.1.37950.1.1.6.2.2.5.4.1.1
		-- 1.3.6.1.4.1.37950.1.1.6.2.2.5.4.1.1
		srvPIphostPId OBJECT-TYPE
			SYNTAX Integer32
			MAX-ACCESS read-write
			STATUS current
			DESCRIPTION
				"Description."
			::= { srvPIphostEntry 1 }

		
--  1.3.6.1.4.1.37950.1.1.6.2.2.5.4.1.2
		-- 1.3.6.1.4.1.37950.1.1.6.2.2.5.4.1.2
		srvPIphostTId OBJECT-TYPE
			SYNTAX Integer32
			MAX-ACCESS read-write
			STATUS current
			DESCRIPTION
				"Description."
			::= { srvPIphostEntry 2 }

		
--  1.3.6.1.4.1.37950.1.1.6.2.2.5.4.1.3
		-- 1.3.6.1.4.1.37950.1.1.6.2.2.5.4.1.3
		srvPIphostTDesc OBJECT-TYPE
			SYNTAX OCTET STRING
			MAX-ACCESS read-write
			STATUS current
			DESCRIPTION
				"Description."
			::= { srvPIphostEntry 3 }

		
--  1.3.6.1.4.1.37950.1.1.6.2.2.5.4.1.4
		-- 1.3.6.1.4.1.37950.1.1.6.2.2.5.4.1.4
		srvPIphostTMode OBJECT-TYPE
			SYNTAX INTEGER
				{
				dhcp(1),
				staticIp(2)
				}
			MAX-ACCESS read-write
			STATUS current
			DESCRIPTION
				"Description."
			::= { srvPIphostEntry 4 }

		
--  1.3.6.1.4.1.37950.1.1.6.2.2.5.4.1.5
		-- 1.3.6.1.4.1.37950.1.1.6.2.2.5.4.1.5
		srvPIphostTIpaddr OBJECT-TYPE
			SYNTAX IpAddress
			MAX-ACCESS read-write
			STATUS current
			DESCRIPTION
				"Description."
			::= { srvPIphostEntry 5 }

		
--  1.3.6.1.4.1.37950.1.1.6.2.2.5.4.1.6
		-- 1.3.6.1.4.1.37950.1.1.6.2.2.5.4.1.6
		srvPIphostTMask OBJECT-TYPE
			SYNTAX IpAddress
			MAX-ACCESS read-write
			STATUS current
			DESCRIPTION
				"Description."
			::= { srvPIphostEntry 6 }

		
--  1.3.6.1.4.1.37950.1.1.6.2.2.5.4.1.7
		-- 1.3.6.1.4.1.37950.1.1.6.2.2.5.4.1.7
		srvPIphostTGateway OBJECT-TYPE
			SYNTAX IpAddress
			MAX-ACCESS read-write
			STATUS current
			DESCRIPTION
				"Description."
			::= { srvPIphostEntry 7 }

		
--  1.3.6.1.4.1.37950.1.1.6.2.2.5.4.1.8
		-- 1.3.6.1.4.1.37950.1.1.6.2.2.5.4.1.8
		srvPIphostTPriDns OBJECT-TYPE
			SYNTAX IpAddress
			MAX-ACCESS read-write
			STATUS current
			DESCRIPTION
				"Description."
			::= { srvPIphostEntry 8 }

		
--  1.3.6.1.4.1.37950.1.1.6.2.2.5.4.1.9
		-- 1.3.6.1.4.1.37950.1.1.6.2.2.5.4.1.9
		srvPIphostTSecDns OBJECT-TYPE
			SYNTAX IpAddress
			MAX-ACCESS read-write
			STATUS current
			DESCRIPTION
				"Description."
			::= { srvPIphostEntry 9 }

		
--  1.3.6.1.4.1.37950.1.1.6.2.2.5.4.1.10
		-- 1.3.6.1.4.1.37950.1.1.6.2.2.5.4.1.10
		srvPIphostTVlan OBJECT-TYPE
			SYNTAX Integer32 (0..4094)
			MAX-ACCESS read-write
			STATUS current
			DESCRIPTION
				"Description."
			::= { srvPIphostEntry 10 }

		
--  1.3.6.1.4.1.37950.1.1.6.2.2.5.4.1.11
		-- 1.3.6.1.4.1.37950.1.1.6.2.2.5.4.1.11
		srvPIphostTVlanPri OBJECT-TYPE
			SYNTAX Integer32 (1..15)
			MAX-ACCESS read-write
			STATUS current
			DESCRIPTION
				"Description."
			::= { srvPIphostEntry 11 }

		
--  1.3.6.1.4.1.37950.1.1.6.2.2.5.5
		-- 1.3.6.1.4.1.37950.1.1.6.2.2.5.5
		srvPortBasicTable OBJECT-TYPE
			SYNTAX SEQUENCE OF SrvPortBasicEntry
			MAX-ACCESS not-accessible
			STATUS current
			DESCRIPTION
				"Description."
			::= { v1600gSrvPShow 5 }

		
--  1.3.6.1.4.1.37950.1.1.6.2.2.5.5.1
		-- 1.3.6.1.4.1.37950.1.1.6.2.2.5.5.1
		srvPortBasicEntry OBJECT-TYPE
			SYNTAX SrvPortBasicEntry
			MAX-ACCESS not-accessible
			STATUS current
			DESCRIPTION
				"Description."
			INDEX { srvPortBasicPId, srvPortBasicInterface }
			::= { srvPortBasicTable 1 }

		
		SrvPortBasicEntry ::=
			SEQUENCE { 
				srvPortBasicPId
					Integer32,
				srvPortBasicInterface
					INTEGER,
				srvPortBasicSpdCfg
					INTEGER,
				srvPortBasicAdmSta
					INTEGER,
				srvPortBasicLoopSta
					INTEGER,
				srvPortBasicUpStrRateLimCir
					Integer32,
				srvPortBasicUpStrRateLimPir
					Integer32,
				srvPortBasicDwStrRateLimCir
					Integer32,
				srvPortBasicDwStrRateLimPir
					Integer32
			 }

--  1.3.6.1.4.1.37950.1.1.6.2.2.5.5.1.1
		-- 1.3.6.1.4.1.37950.1.1.6.2.2.5.5.1.1
		srvPortBasicPId OBJECT-TYPE
			SYNTAX Integer32
			MAX-ACCESS read-write
			STATUS current
			DESCRIPTION
				"Description."
			::= { srvPortBasicEntry 1 }

		
--  1.3.6.1.4.1.37950.1.1.6.2.2.5.5.1.2
		-- 1.3.6.1.4.1.37950.1.1.6.2.2.5.5.1.2
		srvPortBasicInterface OBJECT-TYPE
			SYNTAX INTEGER
				{
				LAN1(1),
				LAN2(2),
				LAN3(3),
				LAN4(4),
				LAN5(5),
				LAN6(6),
				LAN7(7),
				LAN8(8),
				LAN9(9),
				LAN10(10),
				LAN11(11),
				LAN12(12),
				LAN13(13),
				LAN14(14),
				LAN15(15),
				LAN16(16),
				LAN17(17),
				LAN18(18),
				LAN19(19),
				LAN20(20),
				LAN21(21),
				LAN22(22),
				LAN23(23),
				LAN24(24),
				LAN25(25),
				LAN26(26),
				LAN27(27),
				LAN28(28),
				LAN29(29),
				LAN30(30),
				LAN31(31),
				LAN32(32)
				}
			MAX-ACCESS read-write
			STATUS current
			DESCRIPTION
				"Description."
			::= { srvPortBasicEntry 2 }

		
--  1.3.6.1.4.1.37950.1.1.6.2.2.5.5.1.3
		-- 1.3.6.1.4.1.37950.1.1.6.2.2.5.5.1.3
		srvPortBasicSpdCfg OBJECT-TYPE
			SYNTAX INTEGER
				{
				auto(0),
				full-10(1),
				full-100(2),
				full-1000(3),
				full-10g(5),
				full-2point5g(6),
				full-5g(7),
				full-25g(8),
				full-40g(9),
				half-10(17),
				half-100(18),
				half-1000(19)
				}
			MAX-ACCESS read-write
			STATUS current
			DESCRIPTION
				"Description."
			::= { srvPortBasicEntry 3 }

		
--  1.3.6.1.4.1.37950.1.1.6.2.2.5.5.1.4
		-- 1.3.6.1.4.1.37950.1.1.6.2.2.5.5.1.4
		srvPortBasicAdmSta OBJECT-TYPE
			SYNTAX INTEGER
				{
				disable(0),
				enable(1)
				}
			MAX-ACCESS read-write
			STATUS current
			DESCRIPTION
				"Description."
			::= { srvPortBasicEntry 4 }

		
--  1.3.6.1.4.1.37950.1.1.6.2.2.5.5.1.5
		-- 1.3.6.1.4.1.37950.1.1.6.2.2.5.5.1.5
		srvPortBasicLoopSta OBJECT-TYPE
			SYNTAX INTEGER
				{
				disable(0),
				enable(1)
				}
			MAX-ACCESS read-write
			STATUS current
			DESCRIPTION
				"Description."
			::= { srvPortBasicEntry 5 }

		
--  1.3.6.1.4.1.37950.1.1.6.2.2.5.5.1.6
		-- 1.3.6.1.4.1.37950.1.1.6.2.2.5.5.1.6
		srvPortBasicUpStrRateLimCir OBJECT-TYPE
			SYNTAX Integer32
			MAX-ACCESS read-write
			STATUS current
			DESCRIPTION
				"Description."
			::= { srvPortBasicEntry 6 }

		
--  1.3.6.1.4.1.37950.1.1.6.2.2.5.5.1.7
		-- 1.3.6.1.4.1.37950.1.1.6.2.2.5.5.1.7
		srvPortBasicUpStrRateLimPir OBJECT-TYPE
			SYNTAX Integer32
			MAX-ACCESS read-write
			STATUS current
			DESCRIPTION
				"Description."
			::= { srvPortBasicEntry 7 }

		
--  1.3.6.1.4.1.37950.1.1.6.2.2.5.5.1.8
		-- 1.3.6.1.4.1.37950.1.1.6.2.2.5.5.1.8
		srvPortBasicDwStrRateLimCir OBJECT-TYPE
			SYNTAX Integer32
			MAX-ACCESS read-write
			STATUS current
			DESCRIPTION
				"Description."
			::= { srvPortBasicEntry 8 }

		
--  1.3.6.1.4.1.37950.1.1.6.2.2.5.5.1.9
		-- 1.3.6.1.4.1.37950.1.1.6.2.2.5.5.1.9
		srvPortBasicDwStrRateLimPir OBJECT-TYPE
			SYNTAX Integer32
			MAX-ACCESS read-write
			STATUS current
			DESCRIPTION
				"Description."
			::= { srvPortBasicEntry 9 }

		
--  1.3.6.1.4.1.37950.1.1.6.2.2.6
		-- 1.3.6.1.4.1.37950.1.1.6.2.2.6
		v1600gAlarmPTable OBJECT-TYPE
			SYNTAX SEQUENCE OF V1600gAlarmPEntry
			MAX-ACCESS not-accessible
			STATUS current
			DESCRIPTION
				"Description."
			::= { v1600gProfileShow 6 }

		
--  1.3.6.1.4.1.37950.1.1.6.2.2.6.1
		-- 1.3.6.1.4.1.37950.1.1.6.2.2.6.1
		v1600gAlarmPEntry OBJECT-TYPE
			SYNTAX V1600gAlarmPEntry
			MAX-ACCESS not-accessible
			STATUS current
			DESCRIPTION
				"Description."
			INDEX { alarmPIdShow }
			::= { v1600gAlarmPTable 1 }

		
		V1600gAlarmPEntry ::=
			SEQUENCE { 
				alarmPIdShow
					Integer32,
				alarmPNameShow
					OCTET STRING,
				alarmPStateShow
					Integer32,
				alarmPRxShow
					OCTET STRING,
				alarmPTxShow
					OCTET STRING,
				alarmPSfSdShow
					OCTET STRING
			 }

--  1.3.6.1.4.1.37950.1.1.6.2.2.6.1.1
		-- 1.3.6.1.4.1.37950.1.1.6.2.2.6.1.1
		alarmPIdShow OBJECT-TYPE
			SYNTAX Integer32
			MAX-ACCESS read-only
			STATUS current
			DESCRIPTION
				"Description."
			::= { v1600gAlarmPEntry 1 }

		
--  1.3.6.1.4.1.37950.1.1.6.2.2.6.1.2
		-- 1.3.6.1.4.1.37950.1.1.6.2.2.6.1.2
		alarmPNameShow OBJECT-TYPE
			SYNTAX OCTET STRING
			MAX-ACCESS read-only
			STATUS current
			DESCRIPTION
				"Description."
			::= { v1600gAlarmPEntry 2 }

		
--  1.3.6.1.4.1.37950.1.1.6.2.2.6.1.3
		-- 1.3.6.1.4.1.37950.1.1.6.2.2.6.1.3
		alarmPStateShow OBJECT-TYPE
			SYNTAX Integer32
			MAX-ACCESS read-only
			STATUS current
			DESCRIPTION
				"Description."
			::= { v1600gAlarmPEntry 3 }

		
--  1.3.6.1.4.1.37950.1.1.6.2.2.6.1.4
		-- 1.3.6.1.4.1.37950.1.1.6.2.2.6.1.4
		alarmPRxShow OBJECT-TYPE
			SYNTAX OCTET STRING
			MAX-ACCESS read-only
			STATUS current
			DESCRIPTION
				"Description."
			::= { v1600gAlarmPEntry 4 }

		
--  1.3.6.1.4.1.37950.1.1.6.2.2.6.1.5
		-- 1.3.6.1.4.1.37950.1.1.6.2.2.6.1.5
		alarmPTxShow OBJECT-TYPE
			SYNTAX OCTET STRING
			MAX-ACCESS read-only
			STATUS current
			DESCRIPTION
				"Description."
			::= { v1600gAlarmPEntry 5 }

		
--  1.3.6.1.4.1.37950.1.1.6.2.2.6.1.6
		-- 1.3.6.1.4.1.37950.1.1.6.2.2.6.1.6
		alarmPSfSdShow OBJECT-TYPE
			SYNTAX OCTET STRING
			MAX-ACCESS read-only
			STATUS current
			DESCRIPTION
				"Description."
			::= { v1600gAlarmPEntry 6 }

		
--  1.3.6.1.4.1.37950.1.1.6.2.2.7
		-- 1.3.6.1.4.1.37950.1.1.6.2.2.7
		v1600gProfileBindTable OBJECT-TYPE
			SYNTAX SEQUENCE OF V1600gProfileBindEntry
			MAX-ACCESS not-accessible
			STATUS current
			DESCRIPTION
				"Description."
			::= { v1600gProfileShow 7 }

		
--  1.3.6.1.4.1.37950.1.1.6.2.2.7.1
		-- 1.3.6.1.4.1.37950.1.1.6.2.2.7.1
		v1600gProfileBindEntry OBJECT-TYPE
			SYNTAX V1600gProfileBindEntry
			MAX-ACCESS not-accessible
			STATUS current
			DESCRIPTION
				"Description."
			INDEX { profileBindShowPon, profileBindShowOnu }
			::= { v1600gProfileBindTable 1 }

		
		V1600gProfileBindEntry ::=
			SEQUENCE { 
				profileBindShowPon
					Integer32,
				profileBindShowOnu
					Integer32,
				profileBindShowOPN
					OCTET STRING,
				profileBindShowLPN
					OCTET STRING,
				profileBindShowSPN
					OCTET STRING,
				profileBindShowAPN
					OCTET STRING,
				profileBindShowPPN
					OCTET STRING,
				profileBindShowFPN
					OCTET STRING
			 }

--  1.3.6.1.4.1.37950.1.1.6.2.2.7.1.1
		-- 1.3.6.1.4.1.37950.1.1.6.2.2.7.1.1
		profileBindShowPon OBJECT-TYPE
			SYNTAX Integer32
			MAX-ACCESS read-only
			STATUS current
			DESCRIPTION
				"Description."
			::= { v1600gProfileBindEntry 1 }

		
--  1.3.6.1.4.1.37950.1.1.6.2.2.7.1.2
		-- 1.3.6.1.4.1.37950.1.1.6.2.2.7.1.2
		profileBindShowOnu OBJECT-TYPE
			SYNTAX Integer32
			MAX-ACCESS read-only
			STATUS current
			DESCRIPTION
				"Description."
			::= { v1600gProfileBindEntry 2 }

		
--  1.3.6.1.4.1.37950.1.1.6.2.2.7.1.3
		-- 1.3.6.1.4.1.37950.1.1.6.2.2.7.1.3
		profileBindShowOPN OBJECT-TYPE
			SYNTAX OCTET STRING
			MAX-ACCESS read-only
			STATUS current
			DESCRIPTION
				"Description."
			::= { v1600gProfileBindEntry 3 }

		
--  1.3.6.1.4.1.37950.1.1.6.2.2.7.1.4
		-- 1.3.6.1.4.1.37950.1.1.6.2.2.7.1.4
		profileBindShowLPN OBJECT-TYPE
			SYNTAX OCTET STRING
			MAX-ACCESS read-only
			STATUS current
			DESCRIPTION
				"Description."
			::= { v1600gProfileBindEntry 4 }

		
--  1.3.6.1.4.1.37950.1.1.6.2.2.7.1.5
		-- 1.3.6.1.4.1.37950.1.1.6.2.2.7.1.5
		profileBindShowSPN OBJECT-TYPE
			SYNTAX OCTET STRING
			MAX-ACCESS read-only
			STATUS current
			DESCRIPTION
				"Description."
			::= { v1600gProfileBindEntry 5 }

		
--  1.3.6.1.4.1.37950.1.1.6.2.2.7.1.6
		-- 1.3.6.1.4.1.37950.1.1.6.2.2.7.1.6
		profileBindShowAPN OBJECT-TYPE
			SYNTAX OCTET STRING
			MAX-ACCESS read-only
			STATUS current
			DESCRIPTION
				"Description."
			::= { v1600gProfileBindEntry 6 }

		
--  1.3.6.1.4.1.37950.1.1.6.2.2.7.1.7
		-- 1.3.6.1.4.1.37950.1.1.6.2.2.7.1.7
		profileBindShowPPN OBJECT-TYPE
			SYNTAX OCTET STRING
			MAX-ACCESS read-only
			STATUS current
			DESCRIPTION
				"Description."
			::= { v1600gProfileBindEntry 7 }

		
--  1.3.6.1.4.1.37950.1.1.6.2.2.7.1.8
		-- 1.3.6.1.4.1.37950.1.1.6.2.2.7.1.8
		profileBindShowFPN OBJECT-TYPE
			SYNTAX OCTET STRING
			MAX-ACCESS read-write
			STATUS current
			DESCRIPTION
				"Description."
			::= { v1600gProfileBindEntry 8 }

		
--  1.3.6.1.4.1.37950.1.1.6.2.2.8
		-- 1.3.6.1.4.1.37950.1.1.6.2.2.8
		v1600gPriPShow OBJECT IDENTIFIER ::= { v1600gProfileShow 8 }

		
--  1.3.6.1.4.1.37950.1.1.6.2.2.8.1
		-- 1.3.6.1.4.1.37950.1.1.6.2.2.8.1
		priPNameTable OBJECT-TYPE
			SYNTAX SEQUENCE OF PriPNameEntry
			MAX-ACCESS not-accessible
			STATUS current
			DESCRIPTION
				"Description."
			::= { v1600gPriPShow 1 }

		
--  1.3.6.1.4.1.37950.1.1.6.2.2.8.1.1
		-- 1.3.6.1.4.1.37950.1.1.6.2.2.8.1.1
		priPNameEntry OBJECT-TYPE
			SYNTAX PriPNameEntry
			MAX-ACCESS not-accessible
			STATUS current
			DESCRIPTION
				"Description."
			INDEX { priPNamePId }
			::= { priPNameTable 1 }

		
		PriPNameEntry ::=
			SEQUENCE { 
				priPNamePId
					Integer32,
				priPNameTableName
					OCTET STRING
			 }

--  1.3.6.1.4.1.37950.1.1.6.2.2.8.1.1.1
		-- 1.3.6.1.4.1.37950.1.1.6.2.2.8.1.1.1
		priPNamePId OBJECT-TYPE
			SYNTAX Integer32
			MAX-ACCESS read-write
			STATUS current
			DESCRIPTION
				"Description."
			::= { priPNameEntry 1 }

		
--  1.3.6.1.4.1.37950.1.1.6.2.2.8.1.1.2
		-- 1.3.6.1.4.1.37950.1.1.6.2.2.8.1.1.2
		priPNameTableName OBJECT-TYPE
			SYNTAX OCTET STRING
			MAX-ACCESS read-write
			STATUS current
			DESCRIPTION
				"Description."
			::= { priPNameEntry 2 }

		
--   1.3.6.1.4.1.37950.1.1.5.12.3.2.6
-- 1.3.6.1.4.1.37950.1.1.6.2.2.8.2
		-- 1.3.6.1.4.1.37950.1.1.6.2.2.8.2
		priPWanConnTable OBJECT-TYPE
			SYNTAX SEQUENCE OF PriPWanConnEntry
			MAX-ACCESS not-accessible
			STATUS current
			DESCRIPTION
				"Description."
			::= { v1600gPriPShow 2 }

		
--   1.3.6.1.4.1.37950.1.1.5.12.3.2.6.1
-- 1.3.6.1.4.1.37950.1.1.6.2.2.8.2.1
		-- 1.3.6.1.4.1.37950.1.1.6.2.2.8.2.1
		priPWanConnEntry OBJECT-TYPE
			SYNTAX PriPWanConnEntry
			MAX-ACCESS not-accessible
			STATUS current
			DESCRIPTION
				"Description."
			INDEX { priPWanConnPId, priPWanConnIndex }
			::= { priPWanConnTable 1 }

		
		PriPWanConnEntry ::=
			SEQUENCE { 
				priPWanConnPId
					Integer32,
				priPWanConnIndex
					Integer32,
				priPWanConnBindLan
					INTEGER,
				priPWanConnBindSsid
					INTEGER,
				priPWanMode
					INTEGER,
				priPWanConnType
					INTEGER,
				priPWanConnVlanId
					INTEGER,
				priPWanConnVlanCos
					INTEGER,
				priPWanConnNatEnable
					INTEGER,
				priPWanConnMode
					INTEGER,
				priPWanConnIpAddress
					IpAddress,
				priPWanConnIpMask
					IpAddress,
				priPWanConnGateway
					IpAddress,
				priPWanConnMasterDns
					IpAddress,
				priPWanConnSlaveDns
					IpAddress,
				priPWanConnPppoeProxy
					INTEGER,
				priPWanConnPppoeUsername
					OCTET STRING,
				priPWanConnPppoePassword
					OCTET STRING,
				priPWanConnPppoeSerName
					OCTET STRING,
				priPWanConnPppoeMode
					INTEGER,
				priPWanConnQosEnable
					INTEGER,
				priPWanConnVlanMode
					INTEGER,
				priPWanConnTranslationEnable
					INTEGER,
				priPWanConnTranslationVlan
					INTEGER,
				priPWanConnTranslationCos
					INTEGER,
				priPWanConnQinqEnable
					INTEGER,
				priPWanConnQinqTpid
					INTEGER,
				priPiWanConnSvlanId
					INTEGER,
				priPWanConnSvlanCos
					INTEGER,
				priPWanConnMTU
					Integer32
			 }

--   1.3.6.1.4.1.37950.1.1.5.12.3.2.6.1.1
-- 1.3.6.1.4.1.37950.1.1.6.2.2.8.2.1.1
		-- 1.3.6.1.4.1.37950.1.1.6.2.2.8.2.1.1
		priPWanConnPId OBJECT-TYPE
			SYNTAX Integer32
			MAX-ACCESS read-write
			STATUS current
			DESCRIPTION
				"Description."
			::= { priPWanConnEntry 1 }

		
--   1.3.6.1.4.1.37950.1.1.5.12.3.2.6.1.3
-- 1.3.6.1.4.1.37950.1.1.6.2.2.8.2.1.2
		-- 1.3.6.1.4.1.37950.1.1.6.2.2.8.2.1.2
		priPWanConnIndex OBJECT-TYPE
			SYNTAX Integer32 (1..8)
			MAX-ACCESS read-write
			STATUS current
			DESCRIPTION
				"Description."
			::= { priPWanConnEntry 2 }

		
--   1.3.6.1.4.1.37950.1.1.5.12.3.2.6.1.4
-- 1.3.6.1.4.1.37950.1.1.6.2.2.8.2.1.3
		-- 1.3.6.1.4.1.37950.1.1.6.2.2.8.2.1.3
		priPWanConnBindLan OBJECT-TYPE
			SYNTAX INTEGER (0..255)
			MAX-ACCESS read-write
			STATUS current
			DESCRIPTION
				"Description."
			::= { priPWanConnEntry 3 }

		
--   1.3.6.1.4.1.37950.1.1.5.12.3.2.6.1.5
-- 1.3.6.1.4.1.37950.1.1.6.2.2.8.2.1.4
		-- 1.3.6.1.4.1.37950.1.1.6.2.2.8.2.1.4
		priPWanConnBindSsid OBJECT-TYPE
			SYNTAX INTEGER (0..255)
			MAX-ACCESS read-write
			STATUS current
			DESCRIPTION
				"Description."
			::= { priPWanConnEntry 4 }

		
--   1.3.6.1.4.1.37950.1.1.5.12.3.2.6.1.6
-- 1.3.6.1.4.1.37950.1.1.6.2.2.8.2.1.5
		-- 1.3.6.1.4.1.37950.1.1.6.2.2.8.2.1.5
		priPWanMode OBJECT-TYPE
			SYNTAX INTEGER
				{
				internet(0),
				multicast(1),
				tr069(2),
				tr069_internet(3),
				tr069_voip(4),
				voip_internet(5),
				tr069_voip_internet(6),
				voip(7),
				other(100)
				}
			MAX-ACCESS read-write
			STATUS current
			DESCRIPTION
				"Description."
			::= { priPWanConnEntry 5 }

		
--   1.3.6.1.4.1.37950.1.1.5.12.3.2.6.1.7
-- 1.3.6.1.4.1.37950.1.1.6.2.2.8.2.1.6
		-- 1.3.6.1.4.1.37950.1.1.6.2.2.8.2.1.6
		priPWanConnType OBJECT-TYPE
			SYNTAX INTEGER
				{
				bridge(0),
				route(1)
				}
			MAX-ACCESS read-write
			STATUS current
			DESCRIPTION
				"Description."
			::= { priPWanConnEntry 6 }

		
--   1.3.6.1.4.1.37950.1.1.5.12.3.2.6.1.8
-- 1.3.6.1.4.1.37950.1.1.6.2.2.8.2.1.7
		-- 1.3.6.1.4.1.37950.1.1.6.2.2.8.2.1.7
		priPWanConnVlanId OBJECT-TYPE
			SYNTAX INTEGER (0..4095)
			MAX-ACCESS read-write
			STATUS current
			DESCRIPTION
				"Description."
			::= { priPWanConnEntry 7 }

		
--   1.3.6.1.4.1.37950.1.1.5.12.3.2.6.1.9
-- 1.3.6.1.4.1.37950.1.1.6.2.2.8.2.1.8
		-- 1.3.6.1.4.1.37950.1.1.6.2.2.8.2.1.8
		priPWanConnVlanCos OBJECT-TYPE
			SYNTAX INTEGER (0..7)
			MAX-ACCESS read-write
			STATUS current
			DESCRIPTION
				"Description."
			::= { priPWanConnEntry 8 }

		
--   1.3.6.1.4.1.37950.1.1.5.12.3.2.6.1.10
-- 1.3.6.1.4.1.37950.1.1.6.2.2.8.2.1.9
		-- 1.3.6.1.4.1.37950.1.1.6.2.2.8.2.1.9
		priPWanConnNatEnable OBJECT-TYPE
			SYNTAX INTEGER
				{
				disable(0),
				enable(1)
				}
			MAX-ACCESS read-write
			STATUS current
			DESCRIPTION
				"Description."
			::= { priPWanConnEntry 9 }

		
--   1.3.6.1.4.1.37950.1.1.5.12.3.2.6.1.11
-- 1.3.6.1.4.1.37950.1.1.6.2.2.8.2.1.10
		-- 1.3.6.1.4.1.37950.1.1.6.2.2.8.2.1.10
		priPWanConnMode OBJECT-TYPE
			SYNTAX INTEGER
				{
				dhcp(0),
				static(1),
				pppoe(2)
				}
			MAX-ACCESS read-write
			STATUS current
			DESCRIPTION
				"Description."
			::= { priPWanConnEntry 10 }

		
--   1.3.6.1.4.1.37950.1.1.5.12.3.2.6.1.12
-- 1.3.6.1.4.1.37950.1.1.6.2.2.8.2.1.11
		-- 1.3.6.1.4.1.37950.1.1.6.2.2.8.2.1.11
		priPWanConnIpAddress OBJECT-TYPE
			SYNTAX IpAddress
			MAX-ACCESS read-write
			STATUS current
			DESCRIPTION
				"Description."
			::= { priPWanConnEntry 11 }

		
--   1.3.6.1.4.1.37950.1.1.5.12.3.2.6.1.13
-- 1.3.6.1.4.1.37950.1.1.6.2.2.8.2.1.12
		-- 1.3.6.1.4.1.37950.1.1.6.2.2.8.2.1.12
		priPWanConnIpMask OBJECT-TYPE
			SYNTAX IpAddress
			MAX-ACCESS read-write
			STATUS current
			DESCRIPTION
				"Description."
			::= { priPWanConnEntry 12 }

		
--   1.3.6.1.4.1.37950.1.1.5.12.3.2.6.1.14
-- 1.3.6.1.4.1.37950.1.1.6.2.2.8.2.1.13
		-- 1.3.6.1.4.1.37950.1.1.6.2.2.8.2.1.13
		priPWanConnGateway OBJECT-TYPE
			SYNTAX IpAddress
			MAX-ACCESS read-write
			STATUS current
			DESCRIPTION
				"Description."
			::= { priPWanConnEntry 13 }

		
--   1.3.6.1.4.1.37950.1.1.5.12.3.2.6.1.15
-- 1.3.6.1.4.1.37950.1.1.6.2.2.8.2.1.14
		-- 1.3.6.1.4.1.37950.1.1.6.2.2.8.2.1.14
		priPWanConnMasterDns OBJECT-TYPE
			SYNTAX IpAddress
			MAX-ACCESS read-write
			STATUS current
			DESCRIPTION
				"Description."
			::= { priPWanConnEntry 14 }

		
--   1.3.6.1.4.1.37950.1.1.5.12.3.2.6.1.16
-- 1.3.6.1.4.1.37950.1.1.6.2.2.8.2.1.15
		-- 1.3.6.1.4.1.37950.1.1.6.2.2.8.2.1.15
		priPWanConnSlaveDns OBJECT-TYPE
			SYNTAX IpAddress
			MAX-ACCESS read-write
			STATUS current
			DESCRIPTION
				"Description."
			::= { priPWanConnEntry 15 }

		
--   1.3.6.1.4.1.37950.1.1.5.12.3.2.6.1.17
-- 1.3.6.1.4.1.37950.1.1.6.2.2.8.2.1.16
		-- 1.3.6.1.4.1.37950.1.1.6.2.2.8.2.1.16
		priPWanConnPppoeProxy OBJECT-TYPE
			SYNTAX INTEGER
				{
				disable(0),
				enable(1)
				}
			MAX-ACCESS read-write
			STATUS current
			DESCRIPTION
				"Description."
			::= { priPWanConnEntry 16 }

		
--   1.3.6.1.4.1.37950.1.1.5.12.3.2.6.1.18
-- 1.3.6.1.4.1.37950.1.1.6.2.2.8.2.1.17
		-- 1.3.6.1.4.1.37950.1.1.6.2.2.8.2.1.17
		priPWanConnPppoeUsername OBJECT-TYPE
			SYNTAX OCTET STRING
			MAX-ACCESS read-write
			STATUS current
			DESCRIPTION
				"Description."
			::= { priPWanConnEntry 17 }

		
--   1.3.6.1.4.1.37950.1.1.5.12.3.2.6.1.19
-- 1.3.6.1.4.1.37950.1.1.6.2.2.8.2.1.18
		-- 1.3.6.1.4.1.37950.1.1.6.2.2.8.2.1.18
		priPWanConnPppoePassword OBJECT-TYPE
			SYNTAX OCTET STRING
			MAX-ACCESS read-write
			STATUS current
			DESCRIPTION
				"Description."
			::= { priPWanConnEntry 18 }

		
--   1.3.6.1.4.1.37950.1.1.5.12.3.2.6.1.20
-- 1.3.6.1.4.1.37950.1.1.6.2.2.8.2.1.19
		-- 1.3.6.1.4.1.37950.1.1.6.2.2.8.2.1.19
		priPWanConnPppoeSerName OBJECT-TYPE
			SYNTAX OCTET STRING
			MAX-ACCESS read-write
			STATUS current
			DESCRIPTION
				"Description."
			::= { priPWanConnEntry 19 }

		
--   1.3.6.1.4.1.37950.1.1.5.12.3.2.6.1.21
-- 1.3.6.1.4.1.37950.1.1.6.2.2.8.2.1.20
		-- 1.3.6.1.4.1.37950.1.1.6.2.2.8.2.1.20
		priPWanConnPppoeMode OBJECT-TYPE
			SYNTAX INTEGER
				{
				autoConnect(0),
				connectWhenPayload(1)
				}
			MAX-ACCESS read-write
			STATUS current
			DESCRIPTION
				"Description."
			::= { priPWanConnEntry 20 }

		
--   1.3.6.1.4.1.37950.1.1.5.12.3.2.6.1.22
-- 1.3.6.1.4.1.37950.1.1.6.2.2.8.2.1.21
		-- 1.3.6.1.4.1.37950.1.1.6.2.2.8.2.1.21
		priPWanConnQosEnable OBJECT-TYPE
			SYNTAX INTEGER
				{
				disable(0),
				enable(1)
				}
			MAX-ACCESS read-write
			STATUS current
			DESCRIPTION
				"Description."
			::= { priPWanConnEntry 21 }

		
--   1.3.6.1.4.1.37950.1.1.5.12.3.2.6.1.23
-- 1.3.6.1.4.1.37950.1.1.6.2.2.8.2.1.22
		-- 1.3.6.1.4.1.37950.1.1.6.2.2.8.2.1.22
		priPWanConnVlanMode OBJECT-TYPE
			SYNTAX INTEGER
				{
				disable(0),
				tag(1),
				transparent(2)
				}
			MAX-ACCESS read-write
			STATUS current
			DESCRIPTION
				"Description."
			::= { priPWanConnEntry 22 }

		
--   1.3.6.1.4.1.37950.1.1.5.12.3.2.6.1.24
-- 1.3.6.1.4.1.37950.1.1.6.2.2.8.2.1.23
		-- 1.3.6.1.4.1.37950.1.1.6.2.2.8.2.1.23
		priPWanConnTranslationEnable OBJECT-TYPE
			SYNTAX INTEGER
				{
				disable(0),
				enable(1)
				}
			MAX-ACCESS read-write
			STATUS current
			DESCRIPTION
				"Description."
			::= { priPWanConnEntry 23 }

		
--   1.3.6.1.4.1.37950.1.1.5.12.3.2.6.1.25
-- 1.3.6.1.4.1.37950.1.1.6.2.2.8.2.1.24
		-- 1.3.6.1.4.1.37950.1.1.6.2.2.8.2.1.24
		priPWanConnTranslationVlan OBJECT-TYPE
			SYNTAX INTEGER (0..4095)
			MAX-ACCESS read-write
			STATUS current
			DESCRIPTION
				"Description."
			::= { priPWanConnEntry 24 }

		
--   1.3.6.1.4.1.37950.1.1.5.12.3.2.6.1.26
-- 1.3.6.1.4.1.37950.1.1.6.2.2.8.2.1.25
		-- 1.3.6.1.4.1.37950.1.1.6.2.2.8.2.1.25
		priPWanConnTranslationCos OBJECT-TYPE
			SYNTAX INTEGER (0..7)
			MAX-ACCESS read-write
			STATUS current
			DESCRIPTION
				"Description."
			::= { priPWanConnEntry 25 }

		
--   1.3.6.1.4.1.37950.1.1.5.12.3.2.6.1.27
-- 1.3.6.1.4.1.37950.1.1.6.2.2.8.2.1.26
		-- 1.3.6.1.4.1.37950.1.1.6.2.2.8.2.1.26
		priPWanConnQinqEnable OBJECT-TYPE
			SYNTAX INTEGER
				{
				disable(0),
				enable(1)
				}
			MAX-ACCESS read-write
			STATUS current
			DESCRIPTION
				"Description."
			::= { priPWanConnEntry 26 }

		
--   1.3.6.1.4.1.37950.1.1.5.12.3.2.6.1.28
-- 1.3.6.1.4.1.37950.1.1.6.2.2.8.2.1.27
		-- 1.3.6.1.4.1.37950.1.1.6.2.2.8.2.1.27
		priPWanConnQinqTpid OBJECT-TYPE
			SYNTAX INTEGER (0..65534)
			MAX-ACCESS read-write
			STATUS current
			DESCRIPTION
				"Description."
			::= { priPWanConnEntry 27 }

		
--   1.3.6.1.4.1.37950.1.1.5.12.3.2.6.1.29
-- 1.3.6.1.4.1.37950.1.1.6.2.2.8.2.1.28
		-- 1.3.6.1.4.1.37950.1.1.6.2.2.8.2.1.28
		priPiWanConnSvlanId OBJECT-TYPE
			SYNTAX INTEGER (0..4095)
			MAX-ACCESS read-write
			STATUS current
			DESCRIPTION
				"Description."
			::= { priPWanConnEntry 28 }

		
--   1.3.6.1.4.1.37950.1.1.5.12.3.2.6.1.30
-- 1.3.6.1.4.1.37950.1.1.6.2.2.8.2.1.29
		-- 1.3.6.1.4.1.37950.1.1.6.2.2.8.2.1.29
		priPWanConnSvlanCos OBJECT-TYPE
			SYNTAX INTEGER (0..7)
			MAX-ACCESS read-write
			STATUS current
			DESCRIPTION
				"Description."
			::= { priPWanConnEntry 29 }

		
--  1.3.6.1.4.1.37950.1.1.6.2.2.8.2.1.30
		-- 1.3.6.1.4.1.37950.1.1.6.2.2.8.2.1.30
		priPWanConnMTU OBJECT-TYPE
			SYNTAX Integer32
			MAX-ACCESS read-write
			STATUS current
			DESCRIPTION
				"Description."
			::= { priPWanConnEntry 30 }

		
--   1.3.6.1.4.1.37950.1.1.5.12.3.2.9
-- 1.3.6.1.4.1.37950.1.1.6.2.2.8.3
		-- 1.3.6.1.4.1.37950.1.1.6.2.2.8.3
		priPDhcpServerTable OBJECT-TYPE
			SYNTAX SEQUENCE OF PriPDhcpServerEntry
			MAX-ACCESS not-accessible
			STATUS current
			DESCRIPTION
				"Description."
			::= { v1600gPriPShow 3 }

		
--   1.3.6.1.4.1.37950.1.1.5.12.3.2.9.1
-- 1.3.6.1.4.1.37950.1.1.6.2.2.8.3.1
		-- 1.3.6.1.4.1.37950.1.1.6.2.2.8.3.1
		priPDhcpServerEntry OBJECT-TYPE
			SYNTAX PriPDhcpServerEntry
			MAX-ACCESS not-accessible
			STATUS current
			DESCRIPTION
				"Description."
			INDEX { priPDhcpServerPId }
			::= { priPDhcpServerTable 1 }

		
		PriPDhcpServerEntry ::=
			SEQUENCE { 
				priPDhcpServerPId
					Integer32,
				priPDhcpLanIpS
					IpAddress,
				priPDhcpLanMaskS
					IpAddress,
				priPDhcpEnableS
					INTEGER,
				priPDhcpLeaseS
					Unsigned32,
				priPDhcpBeginIpS
					IpAddress,
				priPDhcpEndIpS
					IpAddress,
				priPDhcpPoolTypeS
					INTEGER,
				priPDhcpMasterDnsS
					IpAddress,
				priPDhcpSlaveDnsS
					IpAddress,
				priPDhcpGatewayS
					IpAddress,
				priPDhcpRelayIpS
					IpAddress,
				priPDhcpDnsModeS
					INTEGER
			 }

--   1.3.6.1.4.1.37950.1.1.5.12.3.2.9.1.1
-- 1.3.6.1.4.1.37950.1.1.6.2.2.8.3.1.1
		-- 1.3.6.1.4.1.37950.1.1.6.2.2.8.3.1.1
		priPDhcpServerPId OBJECT-TYPE
			SYNTAX Integer32
			MAX-ACCESS read-write
			STATUS current
			DESCRIPTION
				"Description."
			::= { priPDhcpServerEntry 1 }

		
--   1.3.6.1.4.1.37950.1.1.5.12.3.2.9.1.3
-- 1.3.6.1.4.1.37950.1.1.6.2.2.8.3.1.2
		-- 1.3.6.1.4.1.37950.1.1.6.2.2.8.3.1.2
		priPDhcpLanIpS OBJECT-TYPE
			SYNTAX IpAddress
			MAX-ACCESS read-write
			STATUS current
			DESCRIPTION
				"Description."
			::= { priPDhcpServerEntry 2 }

		
--   1.3.6.1.4.1.37950.1.1.5.12.3.2.9.1.4
-- 1.3.6.1.4.1.37950.1.1.6.2.2.8.3.1.3
		-- 1.3.6.1.4.1.37950.1.1.6.2.2.8.3.1.3
		priPDhcpLanMaskS OBJECT-TYPE
			SYNTAX IpAddress
			MAX-ACCESS read-write
			STATUS current
			DESCRIPTION
				"Description."
			::= { priPDhcpServerEntry 3 }

		
--   1.3.6.1.4.1.37950.1.1.5.12.3.2.9.1.5
-- 1.3.6.1.4.1.37950.1.1.6.2.2.8.3.1.4
		-- 1.3.6.1.4.1.37950.1.1.6.2.2.8.3.1.4
		priPDhcpEnableS OBJECT-TYPE
			SYNTAX INTEGER
				{
				disable(0),
				enable(1),
				relay(2)
				}
			MAX-ACCESS read-write
			STATUS current
			DESCRIPTION
				"Description."
			::= { priPDhcpServerEntry 4 }

		
--   1.3.6.1.4.1.37950.1.1.5.12.3.2.9.1.6
-- 1.3.6.1.4.1.37950.1.1.6.2.2.8.3.1.5
		-- 1.3.6.1.4.1.37950.1.1.6.2.2.8.3.1.5
		priPDhcpLeaseS OBJECT-TYPE
			SYNTAX Unsigned32
			MAX-ACCESS read-write
			STATUS current
			DESCRIPTION
				"Description."
			::= { priPDhcpServerEntry 5 }

		
--   1.3.6.1.4.1.37950.1.1.5.12.3.2.9.1.7
-- 1.3.6.1.4.1.37950.1.1.6.2.2.8.3.1.6
		-- 1.3.6.1.4.1.37950.1.1.6.2.2.8.3.1.6
		priPDhcpBeginIpS OBJECT-TYPE
			SYNTAX IpAddress
			MAX-ACCESS read-write
			STATUS current
			DESCRIPTION
				"Description."
			::= { priPDhcpServerEntry 6 }

		
--   1.3.6.1.4.1.37950.1.1.5.12.3.2.9.1.8
-- 1.3.6.1.4.1.37950.1.1.6.2.2.8.3.1.7
		-- 1.3.6.1.4.1.37950.1.1.6.2.2.8.3.1.7
		priPDhcpEndIpS OBJECT-TYPE
			SYNTAX IpAddress
			MAX-ACCESS read-write
			STATUS current
			DESCRIPTION
				"Description."
			::= { priPDhcpServerEntry 7 }

		
--   1.3.6.1.4.1.37950.1.1.5.12.3.2.9.1.9
-- 1.3.6.1.4.1.37950.1.1.6.2.2.8.3.1.8
		-- 1.3.6.1.4.1.37950.1.1.6.2.2.8.3.1.8
		priPDhcpPoolTypeS OBJECT-TYPE
			SYNTAX INTEGER
				{
				pc(0),
				camera(1),
				stb(2),
				ip_phone(3)
				}
			MAX-ACCESS read-write
			STATUS current
			DESCRIPTION
				"Description."
			::= { priPDhcpServerEntry 8 }

		
--   1.3.6.1.4.1.37950.1.1.5.12.3.2.9.1.10
-- 1.3.6.1.4.1.37950.1.1.6.2.2.8.3.1.9
		-- 1.3.6.1.4.1.37950.1.1.6.2.2.8.3.1.9
		priPDhcpMasterDnsS OBJECT-TYPE
			SYNTAX IpAddress
			MAX-ACCESS read-write
			STATUS current
			DESCRIPTION
				"Description."
			::= { priPDhcpServerEntry 9 }

		
--   1.3.6.1.4.1.37950.1.1.5.12.3.2.9.1.11
-- 1.3.6.1.4.1.37950.1.1.6.2.2.8.3.1.10
		-- 1.3.6.1.4.1.37950.1.1.6.2.2.8.3.1.10
		priPDhcpSlaveDnsS OBJECT-TYPE
			SYNTAX IpAddress
			MAX-ACCESS read-write
			STATUS current
			DESCRIPTION
				"Description."
			::= { priPDhcpServerEntry 10 }

		
--   1.3.6.1.4.1.37950.1.1.5.12.3.2.9.1.12
-- 1.3.6.1.4.1.37950.1.1.6.2.2.8.3.1.11
		-- 1.3.6.1.4.1.37950.1.1.6.2.2.8.3.1.11
		priPDhcpGatewayS OBJECT-TYPE
			SYNTAX IpAddress
			MAX-ACCESS read-write
			STATUS current
			DESCRIPTION
				"Description."
			::= { priPDhcpServerEntry 11 }

		
--   1.3.6.1.4.1.37950.1.1.5.12.3.2.9.1.13
-- 1.3.6.1.4.1.37950.1.1.6.2.2.8.3.1.12
		-- 1.3.6.1.4.1.37950.1.1.6.2.2.8.3.1.12
		priPDhcpRelayIpS OBJECT-TYPE
			SYNTAX IpAddress
			MAX-ACCESS read-write
			STATUS current
			DESCRIPTION
				"Description."
			::= { priPDhcpServerEntry 12 }

		
--  1.3.6.1.4.1.37950.1.1.6.2.2.8.3.1.13
		-- 1.3.6.1.4.1.37950.1.1.6.2.2.8.3.1.13
		priPDhcpDnsModeS OBJECT-TYPE
			SYNTAX INTEGER
				{
				static(0),
				hgw_proxy(1),
				from_isp(2)
				}
			MAX-ACCESS read-write
			STATUS current
			DESCRIPTION
				"Description."
			::= { priPDhcpServerEntry 13 }

		
--   1.3.6.1.4.1.37950.1.1.5.12.3.2.4
-- 1.3.6.1.4.1.37950.1.1.6.2.2.8.4
		-- 1.3.6.1.4.1.37950.1.1.6.2.2.8.4
		priPWifiSwitchTable OBJECT-TYPE
			SYNTAX SEQUENCE OF PriPWifiSwitchEntry
			MAX-ACCESS not-accessible
			STATUS current
			DESCRIPTION
				"Description."
			::= { v1600gPriPShow 4 }

		
--   1.3.6.1.4.1.37950.1.1.5.12.3.2.4.1
-- 1.3.6.1.4.1.37950.1.1.6.2.2.8.4.1
		-- 1.3.6.1.4.1.37950.1.1.6.2.2.8.4.1
		priPWifiSwitchEntry OBJECT-TYPE
			SYNTAX PriPWifiSwitchEntry
			MAX-ACCESS not-accessible
			STATUS current
			DESCRIPTION
				"Description."
			INDEX { priPWifiSwitchPId, priPWifiSwitchNoS }
			::= { priPWifiSwitchTable 1 }

		
		PriPWifiSwitchEntry ::=
			SEQUENCE { 
				priPWifiSwitchPId
					Integer32,
				priPWifiSwitchNoS
					Integer32,
				priPWifiSwitchAPModuleS
					INTEGER,
				priPWifiSwitchCountry
					INTEGER,
				priPWifiSwitchChannelS
					Integer32,
				priPWifiSwitchStandardS
					INTEGER,
				priPWifiSwitchPower
					INTEGER,
				priPWifiSwitchChannelWidthS
					INTEGER,
				priPWifiEasyMeshStatusS
					INTEGER
			 }

--   1.3.6.1.4.1.37950.1.1.5.12.3.2.4.1.1
-- 1.3.6.1.4.1.37950.1.1.6.2.2.8.4.1.1
		-- 1.3.6.1.4.1.37950.1.1.6.2.2.8.4.1.1
		priPWifiSwitchPId OBJECT-TYPE
			SYNTAX Integer32
			MAX-ACCESS read-write
			STATUS current
			DESCRIPTION
				"Description."
			::= { priPWifiSwitchEntry 1 }

		
--  1.3.6.1.4.1.37950.1.1.6.2.2.8.4.1.2
		-- 1.3.6.1.4.1.37950.1.1.6.2.2.8.4.1.2
		priPWifiSwitchNoS OBJECT-TYPE
			SYNTAX Integer32
			MAX-ACCESS read-write
			STATUS current
			DESCRIPTION
				"Description."
			::= { priPWifiSwitchEntry 2 }

		
--   1.3.6.1.4.1.37950.1.1.5.12.3.2.4.1.3
-- 1.3.6.1.4.1.37950.1.1.6.2.2.8.4.1.3
		-- 1.3.6.1.4.1.37950.1.1.6.2.2.8.4.1.3
		priPWifiSwitchAPModuleS OBJECT-TYPE
			SYNTAX INTEGER
				{
				disable(0),
				enable(1)
				}
			MAX-ACCESS read-write
			STATUS current
			DESCRIPTION
				"Description."
			::= { priPWifiSwitchEntry 3 }

		
--   1.3.6.1.4.1.37950.1.1.5.12.3.2.4.1.4
-- 1.3.6.1.4.1.37950.1.1.6.2.2.8.4.1.4
		-- 1.3.6.1.4.1.37950.1.1.6.2.2.8.4.1.4
		priPWifiSwitchCountry OBJECT-TYPE
			SYNTAX INTEGER
				{
				etsi(0),
				fcc(1),
				ic(2),
				spain(3),
				france(4),
				mkk(5),
				isreal(6),
				mkk2(7),
				mkk3(8),
				russian(9),
				cn(10),
				global(11),
				world-wide(12),
				mkk1(13),
				ncc(14)
				}
			MAX-ACCESS read-write
			STATUS current
			DESCRIPTION
				"Description."
			::= { priPWifiSwitchEntry 4 }

		
--   1.3.6.1.4.1.37950.1.1.5.12.3.2.4.1.5
-- 1.3.6.1.4.1.37950.1.1.6.2.2.8.4.1.5
		-- 1.3.6.1.4.1.37950.1.1.6.2.2.8.4.1.5
		priPWifiSwitchChannelS OBJECT-TYPE
			SYNTAX Integer32
			MAX-ACCESS read-write
			STATUS current
			DESCRIPTION
				"Description."
			::= { priPWifiSwitchEntry 5 }

		
--   1.3.6.1.4.1.37950.1.1.5.12.3.2.4.1.6
-- 1.3.6.1.4.1.37950.1.1.6.2.2.8.4.1.6
		-- 1.3.6.1.4.1.37950.1.1.6.2.2.8.4.1.6
		priPWifiSwitchStandardS OBJECT-TYPE
			SYNTAX INTEGER
				{
				s80211b(0),
				s80211g(1),
				s80211bg(2),
				s80211n(3),
				s80211bgn(4),
				s80211ac(5),
				s80211acA(6),
				s80211acN(7),
				s80211acAN(8),
				s80211acNAC(9),
				s80211acANAC(10),
				s80211acax(11),
				s80211acANACax(12),
				s80211ax(13),
				s80211bgnax(14),
				s80211gn(15)
				}
			MAX-ACCESS read-write
			STATUS current
			DESCRIPTION
				"Description."
			::= { priPWifiSwitchEntry 6 }

		
--   1.3.6.1.4.1.37950.1.1.5.12.3.2.4.1.7
-- 1.3.6.1.4.1.37950.1.1.6.2.2.8.4.1.7
		-- 1.3.6.1.4.1.37950.1.1.6.2.2.8.4.1.7
		priPWifiSwitchPower OBJECT-TYPE
			SYNTAX INTEGER (0..20)
			MAX-ACCESS read-write
			STATUS current
			DESCRIPTION
				"Description."
			::= { priPWifiSwitchEntry 7 }

		
--  1.3.6.1.4.1.37950.1.1.6.2.2.8.4.1.8
		-- 1.3.6.1.4.1.37950.1.1.6.2.2.8.4.1.8
		priPWifiSwitchChannelWidthS OBJECT-TYPE
			SYNTAX INTEGER
				{
				s20MHz(0),
				s40MHz(1),
				s80MHz(2),
				s20_40MHz(3),
				s20_40_80MHz(4),
				s160MHz(5)
				}
			MAX-ACCESS read-write
			STATUS current
			DESCRIPTION
				"Description."
			::= { priPWifiSwitchEntry 8 }

		
--  1.3.6.1.4.1.37950.1.1.6.2.2.8.4.1.9
		-- 1.3.6.1.4.1.37950.1.1.6.2.2.8.4.1.9
		priPWifiEasyMeshStatusS OBJECT-TYPE
			SYNTAX INTEGER
				{
				disable(0),
				enable(1)
				}
			MAX-ACCESS read-write
			STATUS current
			DESCRIPTION
				"Description."
			::= { priPWifiSwitchEntry 9 }

		
--   1.3.6.1.4.1.37950.1.1.5.12.3.2.5
-- 1.3.6.1.4.1.37950.1.1.6.2.2.8.5
		-- 1.3.6.1.4.1.37950.1.1.6.2.2.8.5
		priPWifiSsidTable OBJECT-TYPE
			SYNTAX SEQUENCE OF PriPWifiSsidEntry
			MAX-ACCESS not-accessible
			STATUS current
			DESCRIPTION
				"Description."
			::= { v1600gPriPShow 5 }

		
--   1.3.6.1.4.1.37950.1.1.5.12.3.2.5.1
-- 1.3.6.1.4.1.37950.1.1.6.2.2.8.5.1
		-- 1.3.6.1.4.1.37950.1.1.6.2.2.8.5.1
		priPWifiSsidEntry OBJECT-TYPE
			SYNTAX PriPWifiSsidEntry
			MAX-ACCESS not-accessible
			STATUS current
			DESCRIPTION
				"Description."
			INDEX { priPWifiSsidPId, priPWifiSsidIdS }
			::= { priPWifiSsidTable 1 }

		
		PriPWifiSsidEntry ::=
			SEQUENCE { 
				priPWifiSsidPId
					Integer32,
				priPWifiSsidIdS
					Integer32,
				priPWifiSsidNameS
					OCTET STRING,
				priPWifiSsidEnableS
					INTEGER,
				priPWifiSsidHideS
					INTEGER,
				priPWifiSsidAuthMode
					INTEGER,
				priPWifiSsidEncryTpeS
					INTEGER,
				priPSsidPreshareKeyS
					OCTET STRING,
				priPSsidWpaRekeyIntervalS
					INTEGER,
				priPSsidRadiusServIpTypeS
					INTEGER,
				priPSsidRadiusServIp
					IpAddress,
				priPSsidRadiusServIpPrefixLenS
					INTEGER,
				priPSsidRadiusPortS
					INTEGER,
				priPSsidRadiusKeyS
					OCTET STRING,
				priPSsidWepEncryptionLevelS
					INTEGER,
				priPSsidWepKeyIndexS
					INTEGER,
				priPSsidWepKey1S
					OCTET STRING,
				priPSsidWepKey2S
					OCTET STRING,
				priPSsidWepKey3S
					OCTET STRING,
				priPSsidWepKey4S
					OCTET STRING
			 }

--   1.3.6.1.4.1.37950.1.1.5.12.3.2.5.1.1
-- 1.3.6.1.4.1.37950.1.1.6.2.2.8.5.1.1
		-- 1.3.6.1.4.1.37950.1.1.6.2.2.8.5.1.1
		priPWifiSsidPId OBJECT-TYPE
			SYNTAX Integer32
			MAX-ACCESS read-write
			STATUS current
			DESCRIPTION
				"Description."
			::= { priPWifiSsidEntry 1 }

		
--   1.3.6.1.4.1.37950.1.1.5.12.3.2.5.1.3
-- 1.3.6.1.4.1.37950.1.1.6.2.2.8.5.1.2
		-- 1.3.6.1.4.1.37950.1.1.6.2.2.8.5.1.2
		priPWifiSsidIdS OBJECT-TYPE
			SYNTAX Integer32 (1..10)
			MAX-ACCESS read-write
			STATUS current
			DESCRIPTION
				"Description."
			::= { priPWifiSsidEntry 2 }

		
--   1.3.6.1.4.1.37950.1.1.5.12.3.2.5.1.4
-- 1.3.6.1.4.1.37950.1.1.6.2.2.8.5.1.3
		-- 1.3.6.1.4.1.37950.1.1.6.2.2.8.5.1.3
		priPWifiSsidNameS OBJECT-TYPE
			SYNTAX OCTET STRING
			MAX-ACCESS read-write
			STATUS current
			DESCRIPTION
				"Description."
			::= { priPWifiSsidEntry 3 }

		
--   1.3.6.1.4.1.37950.1.1.5.12.3.2.5.1.5
-- 1.3.6.1.4.1.37950.1.1.6.2.2.8.5.1.4
		-- 1.3.6.1.4.1.37950.1.1.6.2.2.8.5.1.4
		priPWifiSsidEnableS OBJECT-TYPE
			SYNTAX INTEGER
				{
				disable(0),
				enable(1)
				}
			MAX-ACCESS read-write
			STATUS current
			DESCRIPTION
				"Description."
			::= { priPWifiSsidEntry 4 }

		
--   1.3.6.1.4.1.37950.1.1.5.12.3.2.5.1.6
-- 1.3.6.1.4.1.37950.1.1.6.2.2.8.5.1.5
		-- 1.3.6.1.4.1.37950.1.1.6.2.2.8.5.1.5
		priPWifiSsidHideS OBJECT-TYPE
			SYNTAX INTEGER
				{
				disable(0),
				enable(1)
				}
			MAX-ACCESS read-write
			STATUS current
			DESCRIPTION
				"Description."
			::= { priPWifiSsidEntry 5 }

		
--   1.3.6.1.4.1.37950.1.1.5.12.3.2.5.1.7
-- 1.3.6.1.4.1.37950.1.1.6.2.2.8.5.1.6
		-- 1.3.6.1.4.1.37950.1.1.6.2.2.8.5.1.6
		priPWifiSsidAuthMode OBJECT-TYPE
			SYNTAX INTEGER
				{
				open(1),
				shared(2),
				wepauto(3),
				wpapsk(4),
				wpa(5),
				wpa2psk(6),
				wpa2(7),
				wpa_wpa2(8),
				wpapsk_wpa2psk(9),
				wpa3psk(10),
				wpa2psk_wpa3psk(11)
				}
			MAX-ACCESS read-write
			STATUS current
			DESCRIPTION
				"Description."
			::= { priPWifiSsidEntry 6 }

		
--   1.3.6.1.4.1.37950.1.1.5.12.3.2.5.1.8
-- 1.3.6.1.4.1.37950.1.1.6.2.2.8.5.1.7
		-- 1.3.6.1.4.1.37950.1.1.6.2.2.8.5.1.7
		priPWifiSsidEncryTpeS OBJECT-TYPE
			SYNTAX INTEGER
				{
				none(1),
				wep(2),
				tkip(3),
				aes(4),
				tkipaes(5)
				}
			MAX-ACCESS read-write
			STATUS current
			DESCRIPTION
				"Description."
			::= { priPWifiSsidEntry 7 }

		
--   1.3.6.1.4.1.37950.1.1.5.12.3.2.5.1.9
-- 1.3.6.1.4.1.37950.1.1.6.2.2.8.5.1.8
		-- 1.3.6.1.4.1.37950.1.1.6.2.2.8.5.1.8
		priPSsidPreshareKeyS OBJECT-TYPE
			SYNTAX OCTET STRING
			MAX-ACCESS read-write
			STATUS current
			DESCRIPTION
				"Description."
			::= { priPWifiSsidEntry 8 }

		
--   1.3.6.1.4.1.37950.1.1.5.12.3.2.5.1.10
-- 1.3.6.1.4.1.37950.1.1.6.2.2.8.5.1.9
		-- 1.3.6.1.4.1.37950.1.1.6.2.2.8.5.1.9
		priPSsidWpaRekeyIntervalS OBJECT-TYPE
			SYNTAX INTEGER (0..4194303)
			MAX-ACCESS read-write
			STATUS current
			DESCRIPTION
				"Description."
			::= { priPWifiSsidEntry 9 }

		
--   1.3.6.1.4.1.37950.1.1.5.12.3.2.5.1.11
-- 1.3.6.1.4.1.37950.1.1.6.2.2.8.5.1.10
		-- 1.3.6.1.4.1.37950.1.1.6.2.2.8.5.1.10
		priPSsidRadiusServIpTypeS OBJECT-TYPE
			SYNTAX INTEGER
				{
				unknown(0),
				ipv4(1),
				ipv6(2),
				ipv4z(3),
				ipv6z(4),
				dns(16)
				}
			MAX-ACCESS read-write
			STATUS current
			DESCRIPTION
				"Description."
			::= { priPWifiSsidEntry 10 }

		
--   1.3.6.1.4.1.37950.1.1.5.12.3.2.5.1.12
-- 1.3.6.1.4.1.37950.1.1.6.2.2.8.5.1.11
		-- 1.3.6.1.4.1.37950.1.1.6.2.2.8.5.1.11
		priPSsidRadiusServIp OBJECT-TYPE
			SYNTAX IpAddress
			MAX-ACCESS read-write
			STATUS current
			DESCRIPTION
				"Description."
			::= { priPWifiSsidEntry 11 }

		
--   1.3.6.1.4.1.37950.1.1.5.12.3.2.5.1.13
-- 1.3.6.1.4.1.37950.1.1.6.2.2.8.5.1.12
		-- 1.3.6.1.4.1.37950.1.1.6.2.2.8.5.1.12
		priPSsidRadiusServIpPrefixLenS OBJECT-TYPE
			SYNTAX INTEGER (0..255)
			MAX-ACCESS read-write
			STATUS current
			DESCRIPTION
				"Description."
			::= { priPWifiSsidEntry 12 }

		
--   1.3.6.1.4.1.37950.1.1.5.12.3.2.5.1.14
-- 1.3.6.1.4.1.37950.1.1.6.2.2.8.5.1.13
		-- 1.3.6.1.4.1.37950.1.1.6.2.2.8.5.1.13
		priPSsidRadiusPortS OBJECT-TYPE
			SYNTAX INTEGER (0..65535)
			MAX-ACCESS read-write
			STATUS current
			DESCRIPTION
				"Description."
			::= { priPWifiSsidEntry 13 }

		
--   1.3.6.1.4.1.37950.1.1.5.12.3.2.5.1.15
-- 1.3.6.1.4.1.37950.1.1.6.2.2.8.5.1.14
		-- 1.3.6.1.4.1.37950.1.1.6.2.2.8.5.1.14
		priPSsidRadiusKeyS OBJECT-TYPE
			SYNTAX OCTET STRING (SIZE (0..32))
			MAX-ACCESS read-write
			STATUS current
			DESCRIPTION
				"Description."
			::= { priPWifiSsidEntry 14 }

		
--   1.3.6.1.4.1.37950.1.1.5.12.3.2.5.1.16
-- 1.3.6.1.4.1.37950.1.1.6.2.2.8.5.1.15
		-- 1.3.6.1.4.1.37950.1.1.6.2.2.8.5.1.15
		priPSsidWepEncryptionLevelS OBJECT-TYPE
			SYNTAX INTEGER
				{
				s64bit(1),
				s128bit(2)
				}
			MAX-ACCESS read-write
			STATUS current
			DESCRIPTION
				"Description."
			::= { priPWifiSsidEntry 15 }

		
--   1.3.6.1.4.1.37950.1.1.5.12.3.2.5.1.17
-- 1.3.6.1.4.1.37950.1.1.6.2.2.8.5.1.16
		-- 1.3.6.1.4.1.37950.1.1.6.2.2.8.5.1.16
		priPSsidWepKeyIndexS OBJECT-TYPE
			SYNTAX INTEGER (1..4)
			MAX-ACCESS read-write
			STATUS current
			DESCRIPTION
				"Description."
			::= { priPWifiSsidEntry 16 }

		
--   1.3.6.1.4.1.37950.1.1.5.12.3.2.5.1.18
-- 1.3.6.1.4.1.37950.1.1.6.2.2.8.5.1.17
		-- 1.3.6.1.4.1.37950.1.1.6.2.2.8.5.1.17
		priPSsidWepKey1S OBJECT-TYPE
			SYNTAX OCTET STRING
			MAX-ACCESS read-write
			STATUS current
			DESCRIPTION
				"Description."
			::= { priPWifiSsidEntry 17 }

		
--   1.3.6.1.4.1.37950.1.1.5.12.3.2.5.1.19
-- 1.3.6.1.4.1.37950.1.1.6.2.2.8.5.1.18
		-- 1.3.6.1.4.1.37950.1.1.6.2.2.8.5.1.18
		priPSsidWepKey2S OBJECT-TYPE
			SYNTAX OCTET STRING
			MAX-ACCESS read-write
			STATUS current
			DESCRIPTION
				"Description."
			::= { priPWifiSsidEntry 18 }

		
--   1.3.6.1.4.1.37950.1.1.5.12.3.2.5.1.20
-- 1.3.6.1.4.1.37950.1.1.6.2.2.8.5.1.19
		-- 1.3.6.1.4.1.37950.1.1.6.2.2.8.5.1.19
		priPSsidWepKey3S OBJECT-TYPE
			SYNTAX OCTET STRING
			MAX-ACCESS read-write
			STATUS current
			DESCRIPTION
				"Description."
			::= { priPWifiSsidEntry 19 }

		
--   1.3.6.1.4.1.37950.1.1.5.12.3.2.5.1.21
-- 1.3.6.1.4.1.37950.1.1.6.2.2.8.5.1.20
		-- 1.3.6.1.4.1.37950.1.1.6.2.2.8.5.1.20
		priPSsidWepKey4S OBJECT-TYPE
			SYNTAX OCTET STRING
			MAX-ACCESS read-write
			STATUS current
			DESCRIPTION
				"Description."
			::= { priPWifiSsidEntry 20 }

		
--   1.3.6.1.4.1.37950.1.1.5.12.3.2.14
-- 1.3.6.1.4.1.37950.1.1.6.2.2.8.6
		-- 1.3.6.1.4.1.37950.1.1.6.2.2.8.6
		priPSipParamTable OBJECT-TYPE
			SYNTAX SEQUENCE OF PriPSipParamEntry
			MAX-ACCESS not-accessible
			STATUS current
			DESCRIPTION
				"Description."
			::= { v1600gPriPShow 6 }

		
--   1.3.6.1.4.1.37950.1.1.5.12.3.2.14.1
-- 1.3.6.1.4.1.37950.1.1.6.2.2.8.6.1
		-- 1.3.6.1.4.1.37950.1.1.6.2.2.8.6.1
		priPSipParamEntry OBJECT-TYPE
			SYNTAX PriPSipParamEntry
			MAX-ACCESS not-accessible
			STATUS current
			DESCRIPTION
				"Description."
			INDEX { priPSipParamPId }
			::= { priPSipParamTable 1 }

		
		PriPSipParamEntry ::=
			SEQUENCE { 
				priPSipParamPId
					Integer32,
				priPSipParamProxyServIp
					OCTET STRING,
				priPSipParamProxyServPort
					Integer32,
				priPSipParamBakProxyServIp
					OCTET STRING,
				priPSipParamBakProxyServPort
					Integer32,
				priPSipParamRegServIp
					OCTET STRING,
				priPSipParamRegServPort
					Integer32,
				priPSipParamBakRegServIp
					OCTET STRING,
				priPSipParamBakRegServPort
					Integer32,
				priPSipParamOutBndServIp
					OCTET STRING,
				priPSipParamOutBndServPort
					Integer32,
				priPSipParamMgPortS
					Integer32,
				priPSipParamRegInterValue
					Integer32
			 }

--   1.3.6.1.4.1.37950.1.1.5.12.3.2.14.1.1
-- 1.3.6.1.4.1.37950.1.1.6.2.2.8.6.1.1
		-- 1.3.6.1.4.1.37950.1.1.6.2.2.8.6.1.1
		priPSipParamPId OBJECT-TYPE
			SYNTAX Integer32
			MAX-ACCESS read-write
			STATUS current
			DESCRIPTION
				"Description."
			::= { priPSipParamEntry 1 }

		
--   1.3.6.1.4.1.37950.1.1.5.12.3.2.14.1.3
-- 1.3.6.1.4.1.37950.1.1.6.2.2.8.6.1.2
		-- 1.3.6.1.4.1.37950.1.1.6.2.2.8.6.1.2
		priPSipParamProxyServIp OBJECT-TYPE
			SYNTAX OCTET STRING
			MAX-ACCESS read-write
			STATUS current
			DESCRIPTION
				"Description."
			::= { priPSipParamEntry 2 }

		
--   1.3.6.1.4.1.37950.1.1.5.12.3.2.14.1.4
-- 1.3.6.1.4.1.37950.1.1.6.2.2.8.6.1.3
		-- 1.3.6.1.4.1.37950.1.1.6.2.2.8.6.1.3
		priPSipParamProxyServPort OBJECT-TYPE
			SYNTAX Integer32 (0..65535)
			MAX-ACCESS read-write
			STATUS current
			DESCRIPTION
				"Description."
			::= { priPSipParamEntry 3 }

		
--   1.3.6.1.4.1.37950.1.1.5.12.3.2.14.1.5
-- 1.3.6.1.4.1.37950.1.1.6.2.2.8.6.1.4
		-- 1.3.6.1.4.1.37950.1.1.6.2.2.8.6.1.4
		priPSipParamBakProxyServIp OBJECT-TYPE
			SYNTAX OCTET STRING
			MAX-ACCESS read-write
			STATUS current
			DESCRIPTION
				"Description."
			::= { priPSipParamEntry 4 }

		
--   1.3.6.1.4.1.37950.1.1.5.12.3.2.14.1.6
-- 1.3.6.1.4.1.37950.1.1.6.2.2.8.6.1.5
		-- 1.3.6.1.4.1.37950.1.1.6.2.2.8.6.1.5
		priPSipParamBakProxyServPort OBJECT-TYPE
			SYNTAX Integer32 (0..65535)
			MAX-ACCESS read-write
			STATUS current
			DESCRIPTION
				"Description."
			::= { priPSipParamEntry 5 }

		
--   1.3.6.1.4.1.37950.1.1.5.12.3.2.14.1.7
-- 1.3.6.1.4.1.37950.1.1.6.2.2.8.6.1.6
		-- 1.3.6.1.4.1.37950.1.1.6.2.2.8.6.1.6
		priPSipParamRegServIp OBJECT-TYPE
			SYNTAX OCTET STRING
			MAX-ACCESS read-write
			STATUS current
			DESCRIPTION
				"Description."
			::= { priPSipParamEntry 6 }

		
--   1.3.6.1.4.1.37950.1.1.5.12.3.2.14.1.8
-- 1.3.6.1.4.1.37950.1.1.6.2.2.8.6.1.7
		-- 1.3.6.1.4.1.37950.1.1.6.2.2.8.6.1.7
		priPSipParamRegServPort OBJECT-TYPE
			SYNTAX Integer32 (0..65535)
			MAX-ACCESS read-write
			STATUS current
			DESCRIPTION
				"Description."
			::= { priPSipParamEntry 7 }

		
--   1.3.6.1.4.1.37950.1.1.5.12.3.2.14.1.9
-- 1.3.6.1.4.1.37950.1.1.6.2.2.8.6.1.8
		-- 1.3.6.1.4.1.37950.1.1.6.2.2.8.6.1.8
		priPSipParamBakRegServIp OBJECT-TYPE
			SYNTAX OCTET STRING
			MAX-ACCESS read-write
			STATUS current
			DESCRIPTION
				"Description."
			::= { priPSipParamEntry 8 }

		
--   1.3.6.1.4.1.37950.1.1.5.12.3.2.14.1.10
-- 1.3.6.1.4.1.37950.1.1.6.2.2.8.6.1.9
		-- 1.3.6.1.4.1.37950.1.1.6.2.2.8.6.1.9
		priPSipParamBakRegServPort OBJECT-TYPE
			SYNTAX Integer32 (0..65535)
			MAX-ACCESS read-write
			STATUS current
			DESCRIPTION
				"Description."
			::= { priPSipParamEntry 9 }

		
--   1.3.6.1.4.1.37950.1.1.5.12.3.2.14.1.11
-- 1.3.6.1.4.1.37950.1.1.6.2.2.8.6.1.10
		-- 1.3.6.1.4.1.37950.1.1.6.2.2.8.6.1.10
		priPSipParamOutBndServIp OBJECT-TYPE
			SYNTAX OCTET STRING
			MAX-ACCESS read-write
			STATUS current
			DESCRIPTION
				"Description."
			::= { priPSipParamEntry 10 }

		
--   1.3.6.1.4.1.37950.1.1.5.12.3.2.14.1.12
-- 1.3.6.1.4.1.37950.1.1.6.2.2.8.6.1.11
		-- 1.3.6.1.4.1.37950.1.1.6.2.2.8.6.1.11
		priPSipParamOutBndServPort OBJECT-TYPE
			SYNTAX Integer32 (0..65535)
			MAX-ACCESS read-write
			STATUS current
			DESCRIPTION
				"Description."
			::= { priPSipParamEntry 11 }

		
--   1.3.6.1.4.1.37950.1.1.5.12.3.2.14.1.13
-- 1.3.6.1.4.1.37950.1.1.6.2.2.8.6.1.12
		-- 1.3.6.1.4.1.37950.1.1.6.2.2.8.6.1.12
		priPSipParamMgPortS OBJECT-TYPE
			SYNTAX Integer32 (0..65535)
			MAX-ACCESS read-write
			STATUS current
			DESCRIPTION
				"Description."
			::= { priPSipParamEntry 12 }

		
--   1.3.6.1.4.1.37950.1.1.5.12.3.2.14.1.15
-- 1.3.6.1.4.1.37950.1.1.6.2.2.8.6.1.13
		-- 1.3.6.1.4.1.37950.1.1.6.2.2.8.6.1.13
		priPSipParamRegInterValue OBJECT-TYPE
			SYNTAX Integer32 (0..10000000)
			MAX-ACCESS read-write
			STATUS current
			DESCRIPTION
				"Description."
			::= { priPSipParamEntry 13 }

		
--  1.3.6.1.4.1.37950.1.1.6.2.2.8.7
		-- 1.3.6.1.4.1.37950.1.1.6.2.2.8.7
		priPSipDigitMapTable OBJECT-TYPE
			SYNTAX SEQUENCE OF PriPSipDigitMapEntry
			MAX-ACCESS not-accessible
			STATUS current
			DESCRIPTION
				"Description."
			::= { v1600gPriPShow 7 }

		
--  1.3.6.1.4.1.37950.1.1.6.2.2.8.7.1
		-- 1.3.6.1.4.1.37950.1.1.6.2.2.8.7.1
		priPSipDigitMapEntry OBJECT-TYPE
			SYNTAX PriPSipDigitMapEntry
			MAX-ACCESS not-accessible
			STATUS current
			DESCRIPTION
				"Description."
			INDEX { priPsipDigitMapPId }
			::= { priPSipDigitMapTable 1 }

		
		PriPSipDigitMapEntry ::=
			SEQUENCE { 
				priPsipDigitMapPId
					Integer32,
				priPsipDigitMapBlock
					OCTET STRING
			 }

--  1.3.6.1.4.1.37950.1.1.6.2.2.8.7.1.1
		-- 1.3.6.1.4.1.37950.1.1.6.2.2.8.7.1.1
		priPsipDigitMapPId OBJECT-TYPE
			SYNTAX Integer32
			MAX-ACCESS read-write
			STATUS current
			DESCRIPTION
				"Description."
			::= { priPSipDigitMapEntry 1 }

		
--  1.3.6.1.4.1.37950.1.1.6.2.2.8.7.1.2
		-- 1.3.6.1.4.1.37950.1.1.6.2.2.8.7.1.2
		priPsipDigitMapBlock OBJECT-TYPE
			SYNTAX OCTET STRING
			MAX-ACCESS read-write
			STATUS current
			DESCRIPTION
				"Description."
			::= { priPSipDigitMapEntry 2 }

		
--   1.3.6.1.4.1.37950.1.1.5.12.6.1.4.2
-- 1.3.6.1.4.1.37950.1.1.6.2.2.8.8
		-- 1.3.6.1.4.1.37950.1.1.6.2.2.8.8
		priPSipUserParamTable OBJECT-TYPE
			SYNTAX SEQUENCE OF PriPSipUserParamEntry
			MAX-ACCESS not-accessible
			STATUS current
			DESCRIPTION
				"Description."
			::= { v1600gPriPShow 8 }

		
--   1.3.6.1.4.1.37950.1.1.5.12.6.1.4.2.1
-- 1.3.6.1.4.1.37950.1.1.6.2.2.8.8.1
		-- 1.3.6.1.4.1.37950.1.1.6.2.2.8.8.1
		priPSipUserParamEntry OBJECT-TYPE
			SYNTAX PriPSipUserParamEntry
			MAX-ACCESS not-accessible
			STATUS current
			DESCRIPTION
				"Description."
			INDEX { priPSipUserParamPId, priPSipUserParamPotsNo }
			::= { priPSipUserParamTable 1 }

		
		PriPSipUserParamEntry ::=
			SEQUENCE { 
				priPSipUserParamPId
					Integer32,
				priPSipUserParamPotsNo
					Integer32,
				priPSipUserParamUserAccount
					OCTET STRING,
				priPSipUserParamUserName
					OCTET STRING,
				priPSipUserParamUserPasswd
					OCTET STRING,
				priPSipUserParamAccountActive
					INTEGER
			 }

--   1.3.6.1.4.1.37950.1.1.5.12.6.1.4.2.1.1
-- 1.3.6.1.4.1.37950.1.1.6.2.2.8.8.1.1
		-- 1.3.6.1.4.1.37950.1.1.6.2.2.8.8.1.1
		priPSipUserParamPId OBJECT-TYPE
			SYNTAX Integer32
			MAX-ACCESS read-only
			STATUS current
			DESCRIPTION
				"Description."
			::= { priPSipUserParamEntry 1 }

		
--   1.3.6.1.4.1.37950.1.1.5.12.6.1.4.2.1.3
-- 1.3.6.1.4.1.37950.1.1.6.2.2.8.8.1.2
		-- 1.3.6.1.4.1.37950.1.1.6.2.2.8.8.1.2
		priPSipUserParamPotsNo OBJECT-TYPE
			SYNTAX Integer32 (1..8)
			MAX-ACCESS read-only
			STATUS current
			DESCRIPTION
				"Description."
			::= { priPSipUserParamEntry 2 }

		
--   1.3.6.1.4.1.37950.1.1.5.12.6.1.4.2.1.4
-- 1.3.6.1.4.1.37950.1.1.6.2.2.8.8.1.3
		-- 1.3.6.1.4.1.37950.1.1.6.2.2.8.8.1.3
		priPSipUserParamUserAccount OBJECT-TYPE
			SYNTAX OCTET STRING
			MAX-ACCESS read-only
			STATUS current
			DESCRIPTION
				"Description."
			::= { priPSipUserParamEntry 3 }

		
--   1.3.6.1.4.1.37950.1.1.5.12.6.1.4.2.1.5
-- 1.3.6.1.4.1.37950.1.1.6.2.2.8.8.1.4
		-- 1.3.6.1.4.1.37950.1.1.6.2.2.8.8.1.4
		priPSipUserParamUserName OBJECT-TYPE
			SYNTAX OCTET STRING
			MAX-ACCESS read-only
			STATUS current
			DESCRIPTION
				"Description."
			::= { priPSipUserParamEntry 4 }

		
--   1.3.6.1.4.1.37950.1.1.5.12.6.1.4.2.1.6
-- 1.3.6.1.4.1.37950.1.1.6.2.2.8.8.1.5
		-- 1.3.6.1.4.1.37950.1.1.6.2.2.8.8.1.5
		priPSipUserParamUserPasswd OBJECT-TYPE
			SYNTAX OCTET STRING
			MAX-ACCESS read-only
			STATUS current
			DESCRIPTION
				"Description."
			::= { priPSipUserParamEntry 5 }

		
--  1.3.6.1.4.1.37950.1.1.6.2.2.8.8.1.6
		-- 1.3.6.1.4.1.37950.1.1.6.2.2.8.8.1.6
		priPSipUserParamAccountActive OBJECT-TYPE
			SYNTAX INTEGER
				{
				disable(0),
				enable(1)
				}
			MAX-ACCESS read-write
			STATUS current
			DESCRIPTION
				"Description."
			::= { priPSipUserParamEntry 6 }

		
--   1.3.6.1.4.1.37950.1.1.5.12.4.2.5
-- 1.3.6.1.4.1.37950.1.1.6.2.2.8.9
		-- 1.3.6.1.4.1.37950.1.1.6.2.2.8.9
		priPPotsParameterTable OBJECT-TYPE
			SYNTAX SEQUENCE OF PriPPotsParameterEntry
			MAX-ACCESS not-accessible
			STATUS current
			DESCRIPTION
				"Description."
			::= { v1600gPriPShow 9 }

		
--   1.3.6.1.4.1.37950.1.1.5.12.4.2.5.1
-- 1.3.6.1.4.1.37950.1.1.6.2.2.8.9.1
		-- 1.3.6.1.4.1.37950.1.1.6.2.2.8.9.1
		priPPotsParameterEntry OBJECT-TYPE
			SYNTAX PriPPotsParameterEntry
			MAX-ACCESS not-accessible
			STATUS current
			DESCRIPTION
				"Description."
			INDEX { priPPotsParamPId, priPPotsParamPotsNo }
			::= { priPPotsParameterTable 1 }

		
		PriPPotsParameterEntry ::=
			SEQUENCE { 
				priPPotsParamPId
					Integer32,
				priPPotsParamPotsNo
					Integer32,
				priPPotsParamVadStatus
					INTEGER,
				priPPotsParamEchoCancle
					INTEGER,
				priPPotsParamInputGain
					Integer32,
				priPPotsParamOutputGain
					Integer32,
				priPPotsParamDtmfMode
					INTEGER
			 }

--   1.3.6.1.4.1.37950.1.1.5.12.4.2.5.1.1
-- 1.3.6.1.4.1.37950.1.1.6.2.2.8.9.1.1
		-- 1.3.6.1.4.1.37950.1.1.6.2.2.8.9.1.1
		priPPotsParamPId OBJECT-TYPE
			SYNTAX Integer32
			MAX-ACCESS read-write
			STATUS current
			DESCRIPTION
				"Description."
			::= { priPPotsParameterEntry 1 }

		
--   1.3.6.1.4.1.37950.1.1.5.12.4.2.5.1.3
-- 1.3.6.1.4.1.37950.1.1.6.2.2.8.9.1.2
		-- 1.3.6.1.4.1.37950.1.1.6.2.2.8.9.1.2
		priPPotsParamPotsNo OBJECT-TYPE
			SYNTAX Integer32 (1..8)
			MAX-ACCESS read-write
			STATUS current
			DESCRIPTION
				"Description."
			::= { priPPotsParameterEntry 2 }

		
--   1.3.6.1.4.1.37950.1.1.5.12.4.2.5.1.4
-- 1.3.6.1.4.1.37950.1.1.6.2.2.8.9.1.3
		-- 1.3.6.1.4.1.37950.1.1.6.2.2.8.9.1.3
		priPPotsParamVadStatus OBJECT-TYPE
			SYNTAX INTEGER
				{
				disable(0),
				enable(1)
				}
			MAX-ACCESS read-write
			STATUS current
			DESCRIPTION
				"Description."
			::= { priPPotsParameterEntry 3 }

		
--   1.3.6.1.4.1.37950.1.1.5.12.4.2.5.1.5
-- 1.3.6.1.4.1.37950.1.1.6.2.2.8.9.1.4
		-- 1.3.6.1.4.1.37950.1.1.6.2.2.8.9.1.4
		priPPotsParamEchoCancle OBJECT-TYPE
			SYNTAX INTEGER
				{
				disable(0),
				enable(1)
				}
			MAX-ACCESS read-write
			STATUS current
			DESCRIPTION
				"Description."
			::= { priPPotsParameterEntry 4 }

		
--   1.3.6.1.4.1.37950.1.1.5.12.4.2.5.1.6
-- 1.3.6.1.4.1.37950.1.1.6.2.2.8.9.1.5
		-- 1.3.6.1.4.1.37950.1.1.6.2.2.8.9.1.5
		priPPotsParamInputGain OBJECT-TYPE
			SYNTAX Integer32 (-32..32)
			MAX-ACCESS read-write
			STATUS current
			DESCRIPTION
				"Description."
			::= { priPPotsParameterEntry 5 }

		
--   1.3.6.1.4.1.37950.1.1.5.12.4.2.5.1.7
-- 1.3.6.1.4.1.37950.1.1.6.2.2.8.9.1.6
		-- 1.3.6.1.4.1.37950.1.1.6.2.2.8.9.1.6
		priPPotsParamOutputGain OBJECT-TYPE
			SYNTAX Integer32 (-32..32)
			MAX-ACCESS read-write
			STATUS current
			DESCRIPTION
				"Description."
			::= { priPPotsParameterEntry 6 }

		
--   1.3.6.1.4.1.37950.1.1.5.12.4.2.5.1.8
-- 1.3.6.1.4.1.37950.1.1.6.2.2.8.9.1.8
		-- 1.3.6.1.4.1.37950.1.1.6.2.2.8.9.1.8
		priPPotsParamDtmfMode OBJECT-TYPE
			SYNTAX INTEGER
				{
				transparent(0),
				rfc2833(1),
				rfc2833_redundancy(2),
				outband(3)
				}
			MAX-ACCESS read-write
			STATUS current
			DESCRIPTION
				"Description."
			::= { priPPotsParameterEntry 8 }

		
--  1.3.6.1.4.1.37950.1.1.6.2.2.8.10
		-- 1.3.6.1.4.1.37950.1.1.6.2.2.8.10
		priPMiscCtrlOpTable OBJECT-TYPE
			SYNTAX SEQUENCE OF PriPMiscCtrlOpEntry
			MAX-ACCESS not-accessible
			STATUS current
			DESCRIPTION
				"Description."
			::= { v1600gPriPShow 10 }

		
--  1.3.6.1.4.1.37950.1.1.6.2.2.8.10.1
		-- 1.3.6.1.4.1.37950.1.1.6.2.2.8.10.1
		priPMiscCtrlOpEntry OBJECT-TYPE
			SYNTAX PriPMiscCtrlOpEntry
			MAX-ACCESS not-accessible
			STATUS current
			DESCRIPTION
				"Description."
			INDEX { priPMiscCtrlOpPId }
			::= { priPMiscCtrlOpTable 1 }

		
		PriPMiscCtrlOpEntry ::=
			SEQUENCE { 
				priPMiscCtrlOpPId
					Integer32,
				priPMiscCtrlOpCatvEnableS
					INTEGER,
				priPMiscCtrlOpIgmpEnableS
					INTEGER,
				priPMiscCtrlOpStpEnableS
					INTEGER,
				priPMiscCtrlOpPortIsoEnableS
					INTEGER,
				priPMiscCtrlOpResetButtonS
					INTEGER
			 }

--  1.3.6.1.4.1.37950.1.1.6.2.2.8.10.1.1
		-- 1.3.6.1.4.1.37950.1.1.6.2.2.8.10.1.1
		priPMiscCtrlOpPId OBJECT-TYPE
			SYNTAX Integer32
			MAX-ACCESS read-write
			STATUS current
			DESCRIPTION
				"Description."
			::= { priPMiscCtrlOpEntry 1 }

		
--  1.3.6.1.4.1.37950.1.1.6.2.2.8.10.1.2
		-- 1.3.6.1.4.1.37950.1.1.6.2.2.8.10.1.2
		priPMiscCtrlOpCatvEnableS OBJECT-TYPE
			SYNTAX INTEGER
				{
				disable(0),
				enable(1)
				}
			MAX-ACCESS read-write
			STATUS current
			DESCRIPTION
				"Description."
			::= { priPMiscCtrlOpEntry 2 }

		
--  1.3.6.1.4.1.37950.1.1.6.2.2.8.10.1.3
		-- 1.3.6.1.4.1.37950.1.1.6.2.2.8.10.1.3
		priPMiscCtrlOpIgmpEnableS OBJECT-TYPE
			SYNTAX INTEGER
				{
				disable(0),
				enable(1)
				}
			MAX-ACCESS read-write
			STATUS current
			DESCRIPTION
				"Description."
			::= { priPMiscCtrlOpEntry 3 }

		
--  1.3.6.1.4.1.37950.1.1.6.2.2.8.10.1.4
		-- 1.3.6.1.4.1.37950.1.1.6.2.2.8.10.1.4
		priPMiscCtrlOpStpEnableS OBJECT-TYPE
			SYNTAX INTEGER
				{
				disable(0),
				enable(1)
				}
			MAX-ACCESS read-write
			STATUS current
			DESCRIPTION
				"Description."
			::= { priPMiscCtrlOpEntry 4 }

		
--  1.3.6.1.4.1.37950.1.1.6.2.2.8.10.1.5
		-- 1.3.6.1.4.1.37950.1.1.6.2.2.8.10.1.5
		priPMiscCtrlOpPortIsoEnableS OBJECT-TYPE
			SYNTAX INTEGER
				{
				disable(0),
				enable(1)
				}
			MAX-ACCESS read-write
			STATUS current
			DESCRIPTION
				"Description."
			::= { priPMiscCtrlOpEntry 5 }

		
--  1.3.6.1.4.1.37950.1.1.6.2.2.8.10.1.6
		-- 1.3.6.1.4.1.37950.1.1.6.2.2.8.10.1.6
		priPMiscCtrlOpResetButtonS OBJECT-TYPE
			SYNTAX INTEGER
				{
				disable(0),
				enable(1)
				}
			MAX-ACCESS read-write
			STATUS current
			DESCRIPTION
				"Description."
			::= { priPMiscCtrlOpEntry 6 }

		
--  1.3.6.1.4.1.37950.1.1.6.2.2.8.11
		-- 1.3.6.1.4.1.37950.1.1.6.2.2.8.11
		priPSpeedLimitTable OBJECT-TYPE
			SYNTAX SEQUENCE OF PriPSpeedLimitEntry
			MAX-ACCESS not-accessible
			STATUS current
			DESCRIPTION
				"Description."
			::= { v1600gPriPShow 11 }

		
--  1.3.6.1.4.1.37950.1.1.6.2.2.8.11.1
		-- 1.3.6.1.4.1.37950.1.1.6.2.2.8.11.1
		priPSpeedLimitEntry OBJECT-TYPE
			SYNTAX PriPSpeedLimitEntry
			MAX-ACCESS not-accessible
			STATUS current
			DESCRIPTION
				"Description."
			INDEX { priPSpeedLimitPId }
			::= { priPSpeedLimitTable 1 }

		
		PriPSpeedLimitEntry ::=
			SEQUENCE { 
				priPSpeedLimitPId
					Integer32,
				priPSpeedLimitUpsLimitS
					Integer32,
				priPSpeedLimitDssLimitS
					Integer32
			 }

--  1.3.6.1.4.1.37950.1.1.6.2.2.8.11.1.1
		-- 1.3.6.1.4.1.37950.1.1.6.2.2.8.11.1.1
		priPSpeedLimitPId OBJECT-TYPE
			SYNTAX Integer32
			MAX-ACCESS read-write
			STATUS current
			DESCRIPTION
				"Description."
			::= { priPSpeedLimitEntry 1 }

		
--  1.3.6.1.4.1.37950.1.1.6.2.2.8.11.1.2
		-- 1.3.6.1.4.1.37950.1.1.6.2.2.8.11.1.2
		priPSpeedLimitUpsLimitS OBJECT-TYPE
			SYNTAX Integer32
			MAX-ACCESS read-write
			STATUS current
			DESCRIPTION
				"Description."
			::= { priPSpeedLimitEntry 2 }

		
--  1.3.6.1.4.1.37950.1.1.6.2.2.8.11.1.3
		-- 1.3.6.1.4.1.37950.1.1.6.2.2.8.11.1.3
		priPSpeedLimitDssLimitS OBJECT-TYPE
			SYNTAX Integer32
			MAX-ACCESS read-write
			STATUS current
			DESCRIPTION
				"Description."
			::= { priPSpeedLimitEntry 3 }

		
--  1.3.6.1.4.1.37950.1.1.6.2.2.8.12
		-- 1.3.6.1.4.1.37950.1.1.6.2.2.8.12
		priPiMacTableTable OBJECT-TYPE
			SYNTAX SEQUENCE OF PriPiMacTableEntry
			MAX-ACCESS not-accessible
			STATUS current
			DESCRIPTION
				"Description."
			::= { v1600gPriPShow 12 }

		
--  1.3.6.1.4.1.37950.1.1.6.2.2.8.12.1
		-- 1.3.6.1.4.1.37950.1.1.6.2.2.8.12.1
		priPiMacTableEntry OBJECT-TYPE
			SYNTAX PriPiMacTableEntry
			MAX-ACCESS not-accessible
			STATUS current
			DESCRIPTION
				"Description."
			INDEX { priPMacTablePId }
			::= { priPiMacTableTable 1 }

		
		PriPiMacTableEntry ::=
			SEQUENCE { 
				priPMacTablePId
					Integer32,
				priPMacTableMacAgingTimeS
					Integer32,
				priPMacTablePonMacLimitS
					Integer32,
				priPiMacTableLanMacLimitS
					Integer32
			 }

--  1.3.6.1.4.1.37950.1.1.6.2.2.8.12.1.1
		-- 1.3.6.1.4.1.37950.1.1.6.2.2.8.12.1.1
		priPMacTablePId OBJECT-TYPE
			SYNTAX Integer32
			MAX-ACCESS read-write
			STATUS current
			DESCRIPTION
				"Description."
			::= { priPiMacTableEntry 1 }

		
--  1.3.6.1.4.1.37950.1.1.6.2.2.8.12.1.2
		-- 1.3.6.1.4.1.37950.1.1.6.2.2.8.12.1.2
		priPMacTableMacAgingTimeS OBJECT-TYPE
			SYNTAX Integer32
			MAX-ACCESS read-write
			STATUS current
			DESCRIPTION
				"Description."
			::= { priPiMacTableEntry 2 }

		
--  1.3.6.1.4.1.37950.1.1.6.2.2.8.12.1.3
		-- 1.3.6.1.4.1.37950.1.1.6.2.2.8.12.1.3
		priPMacTablePonMacLimitS OBJECT-TYPE
			SYNTAX Integer32
			MAX-ACCESS read-write
			STATUS current
			DESCRIPTION
				"Description."
			::= { priPiMacTableEntry 3 }

		
--  1.3.6.1.4.1.37950.1.1.6.2.2.8.12.1.4
		-- 1.3.6.1.4.1.37950.1.1.6.2.2.8.12.1.4
		priPiMacTableLanMacLimitS OBJECT-TYPE
			SYNTAX Integer32
			MAX-ACCESS read-write
			STATUS current
			DESCRIPTION
				"Description."
			::= { priPiMacTableEntry 4 }

		
--  1.3.6.1.4.1.37950.1.1.6.2.2.8.13
		-- 1.3.6.1.4.1.37950.1.1.6.2.2.8.13
		priPUsernameTable OBJECT-TYPE
			SYNTAX SEQUENCE OF PriPUsernameEntry
			MAX-ACCESS not-accessible
			STATUS current
			DESCRIPTION
				"Description."
			::= { v1600gPriPShow 13 }

		
--  1.3.6.1.4.1.37950.1.1.6.2.2.8.13.1
		-- 1.3.6.1.4.1.37950.1.1.6.2.2.8.13.1
		priPUsernameEntry OBJECT-TYPE
			SYNTAX PriPUsernameEntry
			MAX-ACCESS not-accessible
			STATUS current
			DESCRIPTION
				"Description."
			INDEX { priPUsernamePId }
			::= { priPUsernameTable 1 }

		
		PriPUsernameEntry ::=
			SEQUENCE { 
				priPUsernamePId
					Integer32,
				priPAdminCtlS
					INTEGER,
				priPAdminNameS
					OCTET STRING,
				priPAdminPwdS
					OCTET STRING,
				priPUserCtlS
					INTEGER,
				priPUserNameS
					OCTET STRING,
				priPUserPwdS
					OCTET STRING
			 }

--  1.3.6.1.4.1.37950.1.1.6.2.2.8.13.1.1
		-- 1.3.6.1.4.1.37950.1.1.6.2.2.8.13.1.1
		priPUsernamePId OBJECT-TYPE
			SYNTAX Integer32
			MAX-ACCESS read-write
			STATUS current
			DESCRIPTION
				"Description."
			::= { priPUsernameEntry 1 }

		
--  1.3.6.1.4.1.37950.1.1.6.2.2.8.13.1.2
		-- 1.3.6.1.4.1.37950.1.1.6.2.2.8.13.1.2
		priPAdminCtlS OBJECT-TYPE
			SYNTAX INTEGER
				{
				disable(0),
				enable(1)
				}
			MAX-ACCESS read-write
			STATUS current
			DESCRIPTION
				"Description."
			::= { priPUsernameEntry 2 }

		
--  1.3.6.1.4.1.37950.1.1.6.2.2.8.13.1.3
		-- 1.3.6.1.4.1.37950.1.1.6.2.2.8.13.1.3
		priPAdminNameS OBJECT-TYPE
			SYNTAX OCTET STRING
			MAX-ACCESS read-write
			STATUS current
			DESCRIPTION
				"Description."
			::= { priPUsernameEntry 3 }

		
--  1.3.6.1.4.1.37950.1.1.6.2.2.8.13.1.4
		-- 1.3.6.1.4.1.37950.1.1.6.2.2.8.13.1.4
		priPAdminPwdS OBJECT-TYPE
			SYNTAX OCTET STRING
			MAX-ACCESS read-write
			STATUS current
			DESCRIPTION
				"Description."
			::= { priPUsernameEntry 4 }

		
--  1.3.6.1.4.1.37950.1.1.6.2.2.8.13.1.5
		-- 1.3.6.1.4.1.37950.1.1.6.2.2.8.13.1.5
		priPUserCtlS OBJECT-TYPE
			SYNTAX INTEGER
				{
				disable(0),
				enable(1)
				}
			MAX-ACCESS read-write
			STATUS current
			DESCRIPTION
				"Description."
			::= { priPUsernameEntry 5 }

		
--  1.3.6.1.4.1.37950.1.1.6.2.2.8.13.1.6
		-- 1.3.6.1.4.1.37950.1.1.6.2.2.8.13.1.6
		priPUserNameS OBJECT-TYPE
			SYNTAX OCTET STRING
			MAX-ACCESS read-write
			STATUS current
			DESCRIPTION
				"Description."
			::= { priPUsernameEntry 6 }

		
--  1.3.6.1.4.1.37950.1.1.6.2.2.8.13.1.7
		-- 1.3.6.1.4.1.37950.1.1.6.2.2.8.13.1.7
		priPUserPwdS OBJECT-TYPE
			SYNTAX OCTET STRING
			MAX-ACCESS read-write
			STATUS current
			DESCRIPTION
				"Description."
			::= { priPUsernameEntry 7 }

		
--  1.3.6.1.4.1.37950.1.1.6.2.2.8.14
		-- 1.3.6.1.4.1.37950.1.1.6.2.2.8.14
		priPriFirewallTable OBJECT-TYPE
			SYNTAX SEQUENCE OF PriPriFirewallEntry
			MAX-ACCESS not-accessible
			STATUS current
			DESCRIPTION
				"Description."
			::= { v1600gPriPShow 14 }

		
--  1.3.6.1.4.1.37950.1.1.6.2.2.8.14.1
		-- 1.3.6.1.4.1.37950.1.1.6.2.2.8.14.1
		priPriFirewallEntry OBJECT-TYPE
			SYNTAX PriPriFirewallEntry
			MAX-ACCESS not-accessible
			STATUS current
			DESCRIPTION
				"Description."
			INDEX { priPriFirewallPId }
			::= { priPriFirewallTable 1 }

		
		PriPriFirewallEntry ::=
			SEQUENCE { 
				priPriFirewallPId
					Integer32,
				priPFirewallS
					INTEGER
			 }

--  1.3.6.1.4.1.37950.1.1.6.2.2.8.14.1.1
		-- 1.3.6.1.4.1.37950.1.1.6.2.2.8.14.1.1
		priPriFirewallPId OBJECT-TYPE
			SYNTAX Integer32
			MAX-ACCESS read-write
			STATUS current
			DESCRIPTION
				"Description."
			::= { priPriFirewallEntry 1 }

		
--  1.3.6.1.4.1.37950.1.1.6.2.2.8.14.1.2
		-- 1.3.6.1.4.1.37950.1.1.6.2.2.8.14.1.2
		priPFirewallS OBJECT-TYPE
			SYNTAX INTEGER
				{
				disable(0),
				low(1),
				middle(2),
				high(3)
				}
			MAX-ACCESS read-write
			STATUS current
			DESCRIPTION
				"Description."
			::= { priPriFirewallEntry 2 }

		
--  1.3.6.1.4.1.37950.1.1.6.2.2.8.15
		-- 1.3.6.1.4.1.37950.1.1.6.2.2.8.15
		priPriAclTable OBJECT-TYPE
			SYNTAX SEQUENCE OF PriPriAclEntry
			MAX-ACCESS not-accessible
			STATUS current
			DESCRIPTION
				"Description."
			::= { v1600gPriPShow 15 }

		
--  1.3.6.1.4.1.37950.1.1.6.2.2.8.15.1
		-- 1.3.6.1.4.1.37950.1.1.6.2.2.8.15.1
		priPriAclEntry OBJECT-TYPE
			SYNTAX PriPriAclEntry
			MAX-ACCESS not-accessible
			STATUS current
			DESCRIPTION
				"Description."
			INDEX { priPriAclPId, priPAclProtocolS }
			::= { priPriAclTable 1 }

		
		PriPriAclEntry ::=
			SEQUENCE { 
				priPriAclPId
					Integer32,
				priPAclProtocolS
					INTEGER,
				priPAclControlS
					INTEGER,
				priPAclLanControlS
					INTEGER,
				priPAclWanControlS
					INTEGER,
				priPAclaclIPv4ControlS
					INTEGER,
				priPAclIPv4AddrS
					IpAddress,
				priPAclIPv4MaskS
					IpAddress,
				priPAclIPv6ControlS
					INTEGER,
				priPAclIPv6AddrS
					OCTET STRING,
				priPAclProtocolPortS
					Unsigned32
			 }

--  1.3.6.1.4.1.37950.1.1.6.2.2.8.15.1.1
		-- 1.3.6.1.4.1.37950.1.1.6.2.2.8.15.1.1
		priPriAclPId OBJECT-TYPE
			SYNTAX Integer32
			MAX-ACCESS read-write
			STATUS current
			DESCRIPTION
				"Description."
			::= { priPriAclEntry 1 }

		
--  1.3.6.1.4.1.37950.1.1.6.2.2.8.15.1.2
		-- 1.3.6.1.4.1.37950.1.1.6.2.2.8.15.1.2
		priPAclProtocolS OBJECT-TYPE
			SYNTAX INTEGER
				{
				ping(0),
				telnet(1),
				ftp(2),
				http(3),
				https(4),
				tftp(5),
				ssh(6)
				}
			MAX-ACCESS read-write
			STATUS current
			DESCRIPTION
				"Description."
			::= { priPriAclEntry 2 }

		
--  1.3.6.1.4.1.37950.1.1.6.2.2.8.15.1.3
		-- 1.3.6.1.4.1.37950.1.1.6.2.2.8.15.1.3
		priPAclControlS OBJECT-TYPE
			SYNTAX INTEGER
				{
				disable(0),
				enable(1)
				}
			MAX-ACCESS read-write
			STATUS current
			DESCRIPTION
				"Description."
			::= { priPriAclEntry 3 }

		
--  1.3.6.1.4.1.37950.1.1.6.2.2.8.15.1.4
		-- 1.3.6.1.4.1.37950.1.1.6.2.2.8.15.1.4
		priPAclLanControlS OBJECT-TYPE
			SYNTAX INTEGER
				{
				disable(0),
				enable(1)
				}
			MAX-ACCESS read-write
			STATUS current
			DESCRIPTION
				"Description."
			::= { priPriAclEntry 4 }

		
--  1.3.6.1.4.1.37950.1.1.6.2.2.8.15.1.5
		-- 1.3.6.1.4.1.37950.1.1.6.2.2.8.15.1.5
		priPAclWanControlS OBJECT-TYPE
			SYNTAX INTEGER
				{
				disable(0),
				enable(1)
				}
			MAX-ACCESS read-write
			STATUS current
			DESCRIPTION
				"Description."
			::= { priPriAclEntry 5 }

		
--  1.3.6.1.4.1.37950.1.1.6.2.2.8.15.1.6
		-- 1.3.6.1.4.1.37950.1.1.6.2.2.8.15.1.6
		priPAclaclIPv4ControlS OBJECT-TYPE
			SYNTAX INTEGER
				{
				disable(0),
				enable(1)
				}
			MAX-ACCESS read-write
			STATUS current
			DESCRIPTION
				"Description."
			::= { priPriAclEntry 6 }

		
--  1.3.6.1.4.1.37950.1.1.6.2.2.8.15.1.7
		-- 1.3.6.1.4.1.37950.1.1.6.2.2.8.15.1.7
		priPAclIPv4AddrS OBJECT-TYPE
			SYNTAX IpAddress
			MAX-ACCESS read-write
			STATUS current
			DESCRIPTION
				"Description."
			::= { priPriAclEntry 7 }

		
--  1.3.6.1.4.1.37950.1.1.6.2.2.8.15.1.8
		-- 1.3.6.1.4.1.37950.1.1.6.2.2.8.15.1.8
		priPAclIPv4MaskS OBJECT-TYPE
			SYNTAX IpAddress
			MAX-ACCESS read-write
			STATUS current
			DESCRIPTION
				"Description."
			::= { priPriAclEntry 8 }

		
--  1.3.6.1.4.1.37950.1.1.6.2.2.8.15.1.9
		-- 1.3.6.1.4.1.37950.1.1.6.2.2.8.15.1.9
		priPAclIPv6ControlS OBJECT-TYPE
			SYNTAX INTEGER
				{
				disable(0),
				enable(1)
				}
			MAX-ACCESS read-write
			STATUS current
			DESCRIPTION
				"Description."
			::= { priPriAclEntry 9 }

		
--  1.3.6.1.4.1.37950.1.1.6.2.2.8.15.1.10
		-- 1.3.6.1.4.1.37950.1.1.6.2.2.8.15.1.10
		priPAclIPv6AddrS OBJECT-TYPE
			SYNTAX OCTET STRING
			MAX-ACCESS read-write
			STATUS current
			DESCRIPTION
				"Description."
			::= { priPriAclEntry 10 }

		
--  1.3.6.1.4.1.37950.1.1.6.2.2.8.15.1.11
		-- 1.3.6.1.4.1.37950.1.1.6.2.2.8.15.1.11
		priPAclProtocolPortS OBJECT-TYPE
			SYNTAX Unsigned32 (0..65535)
			MAX-ACCESS read-write
			STATUS current
			DESCRIPTION
				"Description."
			::= { priPriAclEntry 11 }

		
--  1.3.6.1.4.1.37950.1.1.6.2.2.8.16
		-- 1.3.6.1.4.1.37950.1.1.6.2.2.8.16
		priPWanConnV6Table OBJECT-TYPE
			SYNTAX SEQUENCE OF PriPWanConnV6Entry
			MAX-ACCESS not-accessible
			STATUS current
			DESCRIPTION
				"Description."
			::= { v1600gPriPShow 16 }

		
--  1.3.6.1.4.1.37950.1.1.6.2.2.8.16.1
		-- 1.3.6.1.4.1.37950.1.1.6.2.2.8.16.1
		priPWanConnV6Entry OBJECT-TYPE
			SYNTAX PriPWanConnV6Entry
			MAX-ACCESS not-accessible
			STATUS current
			DESCRIPTION
				"Description."
			INDEX { priPWanConnV6PId, v6wanConnIndexS }
			::= { priPWanConnV6Table 1 }

		
		PriPWanConnV6Entry ::=
			SEQUENCE { 
				priPWanConnV6PId
					Integer32,
				v6wanConnIndexS
					Integer32,
				v6wanConnBindLanS
					INTEGER,
				v6wanConnBindSsidS
					INTEGER,
				v6WanModeS
					INTEGER,
				v6wanConnTypeS
					INTEGER,
				v6wanConnVlanIdS
					INTEGER,
				v6wanConnVlanCosS
					INTEGER,
				v6wanConnIpProtocolS
					INTEGER,
				v6WanConnModeS
					INTEGER,
				v6wanConnIpAddressIpv4S
					IpAddress,
				v6wanConnIpNetMaskIpv4S
					IpAddress,
				v6wanConnGatewayIpv4S
					IpAddress,
				v6wanConnDnsEnableIpv4S
					INTEGER,
				v6wanConnMasterDnsIpv4S
					IpAddress,
				v6wanConnSlaveDnsIpv4S
					IpAddress,
				v6wanConnNatEnableS
					INTEGER,
				v6wanConnAddressIpv6S
					OCTET STRING,
				v6wanConnPrefixLenIpv6S
					INTEGER,
				v6wanConnGatewayIpv6S
					OCTET STRING,
				v6wanConnDnsEnableIpv6S
					INTEGER,
				v6wanConnMsaterDnsIpv6S
					OCTET STRING,
				v6wanConnSlaveDnsIpv6S
					OCTET STRING,
				v6wanConnSlaacS
					INTEGER,
				v6wanConnPppoeProxyS
					INTEGER,
				v6wanConnPppoeUsernameS
					OCTET STRING,
				v6wanConnPppoePasswordS
					OCTET STRING,
				v6wanConnPppoeSerNameS
					OCTET STRING,
				v6wanConnPppoeModeS
					INTEGER,
				v6wanConnDhcpv6ClientAddressS
					INTEGER,
				v6wanConnDhcpv6ClientPrefixS
					INTEGER,
				v6wanConnDsLiteEnableS
					INTEGER,
				v6wanConnDsLiteAftrModeS
					INTEGER,
				v6wanConnDsLiteAddressTypeS
					INTEGER,
				v6wanConnDsLiteAddressS
					OCTET STRING,
				v6wanConnQosEnableS
					INTEGER,
				v6wanConnVlanModeS
					INTEGER,
				v6wanConnTranslationEnableS
					INTEGER,
				v6wanConnTranslationVlanS
					INTEGER,
				v6wanConnTranslationCosS
					INTEGER,
				v6wanConnQinqEnableS
					INTEGER,
				v6wanConnQinqTpidS
					INTEGER,
				v6wanConnSvlanIdS
					INTEGER,
				v6wanConnSvlanCosS
					INTEGER,
				v6wanConnRouteMtuS
					Integer32
			 }

--  1.3.6.1.4.1.37950.1.1.6.2.2.8.16.1.1
		-- 1.3.6.1.4.1.37950.1.1.6.2.2.8.16.1.1
		priPWanConnV6PId OBJECT-TYPE
			SYNTAX Integer32
			MAX-ACCESS read-write
			STATUS current
			DESCRIPTION
				"Description."
			::= { priPWanConnV6Entry 1 }

		
--  1.3.6.1.4.1.37950.1.1.6.2.2.8.16.1.2
		-- 1.3.6.1.4.1.37950.1.1.6.2.2.8.16.1.2
		v6wanConnIndexS OBJECT-TYPE
			SYNTAX Integer32 (1..8)
			MAX-ACCESS read-write
			STATUS current
			DESCRIPTION
				"Description."
			::= { priPWanConnV6Entry 2 }

		
--  1.3.6.1.4.1.37950.1.1.6.2.2.8.16.1.3
		-- 1.3.6.1.4.1.37950.1.1.6.2.2.8.16.1.3
		v6wanConnBindLanS OBJECT-TYPE
			SYNTAX INTEGER (0..65535)
			MAX-ACCESS read-write
			STATUS current
			DESCRIPTION
				"Description."
			::= { priPWanConnV6Entry 3 }

		
--  1.3.6.1.4.1.37950.1.1.6.2.2.8.16.1.4
		-- 1.3.6.1.4.1.37950.1.1.6.2.2.8.16.1.4
		v6wanConnBindSsidS OBJECT-TYPE
			SYNTAX INTEGER (0..65535)
			MAX-ACCESS read-write
			STATUS current
			DESCRIPTION
				"Description."
			::= { priPWanConnV6Entry 4 }

		
--  1.3.6.1.4.1.37950.1.1.6.2.2.8.16.1.5
		-- 1.3.6.1.4.1.37950.1.1.6.2.2.8.16.1.5
		v6WanModeS OBJECT-TYPE
			SYNTAX INTEGER
				{
				internet(0),
				multicast(1),
				tr069(2),
				tr069_internet(3),
				tr069_voip(4),
				voip_internet(5),
				tr069_voip_internet(6),
				voip(7),
				other(100)
				}
			MAX-ACCESS read-write
			STATUS current
			DESCRIPTION
				"Description."
			::= { priPWanConnV6Entry 5 }

		
--  1.3.6.1.4.1.37950.1.1.6.2.2.8.16.1.6
		-- 1.3.6.1.4.1.37950.1.1.6.2.2.8.16.1.6
		v6wanConnTypeS OBJECT-TYPE
			SYNTAX INTEGER
				{
				bridge(0),
				route(1)
				}
			MAX-ACCESS read-write
			STATUS current
			DESCRIPTION
				"Description."
			::= { priPWanConnV6Entry 6 }

		
--  1.3.6.1.4.1.37950.1.1.6.2.2.8.16.1.7
		-- 1.3.6.1.4.1.37950.1.1.6.2.2.8.16.1.7
		v6wanConnVlanIdS OBJECT-TYPE
			SYNTAX INTEGER (0..4095)
			MAX-ACCESS read-write
			STATUS current
			DESCRIPTION
				"Description."
			::= { priPWanConnV6Entry 7 }

		
--  1.3.6.1.4.1.37950.1.1.6.2.2.8.16.1.8
		-- 1.3.6.1.4.1.37950.1.1.6.2.2.8.16.1.8
		v6wanConnVlanCosS OBJECT-TYPE
			SYNTAX INTEGER (0..7)
			MAX-ACCESS read-write
			STATUS current
			DESCRIPTION
				"Description."
			::= { priPWanConnV6Entry 8 }

		
--  1.3.6.1.4.1.37950.1.1.6.2.2.8.16.1.9
		-- 1.3.6.1.4.1.37950.1.1.6.2.2.8.16.1.9
		v6wanConnIpProtocolS OBJECT-TYPE
			SYNTAX INTEGER
				{
				ipv4(0),
				ipv6(1),
				ipv4_ipv6(2)
				}
			MAX-ACCESS read-write
			STATUS current
			DESCRIPTION
				"Description."
			::= { priPWanConnV6Entry 9 }

		
--  1.3.6.1.4.1.37950.1.1.6.2.2.8.16.1.10
		-- 1.3.6.1.4.1.37950.1.1.6.2.2.8.16.1.10
		v6WanConnModeS OBJECT-TYPE
			SYNTAX INTEGER
				{
				dhcp(0),
				static(1),
				pppoe(2)
				}
			MAX-ACCESS read-write
			STATUS current
			DESCRIPTION
				"Description."
			::= { priPWanConnV6Entry 10 }

		
--  1.3.6.1.4.1.37950.1.1.6.2.2.8.16.1.11
		-- 1.3.6.1.4.1.37950.1.1.6.2.2.8.16.1.11
		v6wanConnIpAddressIpv4S OBJECT-TYPE
			SYNTAX IpAddress
			MAX-ACCESS read-write
			STATUS current
			DESCRIPTION
				"Description."
			::= { priPWanConnV6Entry 11 }

		
--  1.3.6.1.4.1.37950.1.1.6.2.2.8.16.1.12
		-- 1.3.6.1.4.1.37950.1.1.6.2.2.8.16.1.12
		v6wanConnIpNetMaskIpv4S OBJECT-TYPE
			SYNTAX IpAddress
			MAX-ACCESS read-write
			STATUS current
			DESCRIPTION
				"Description."
			::= { priPWanConnV6Entry 12 }

		
--  1.3.6.1.4.1.37950.1.1.6.2.2.8.16.1.13
		-- 1.3.6.1.4.1.37950.1.1.6.2.2.8.16.1.13
		v6wanConnGatewayIpv4S OBJECT-TYPE
			SYNTAX IpAddress
			MAX-ACCESS read-write
			STATUS current
			DESCRIPTION
				"Description."
			::= { priPWanConnV6Entry 13 }

		
--  1.3.6.1.4.1.37950.1.1.6.2.2.8.16.1.14
		-- 1.3.6.1.4.1.37950.1.1.6.2.2.8.16.1.14
		v6wanConnDnsEnableIpv4S OBJECT-TYPE
			SYNTAX INTEGER
				{
				disable(0),
				enable(1)
				}
			MAX-ACCESS read-write
			STATUS current
			DESCRIPTION
				"Description."
			::= { priPWanConnV6Entry 14 }

		
--  1.3.6.1.4.1.37950.1.1.6.2.2.8.16.1.15
		-- 1.3.6.1.4.1.37950.1.1.6.2.2.8.16.1.15
		v6wanConnMasterDnsIpv4S OBJECT-TYPE
			SYNTAX IpAddress
			MAX-ACCESS read-write
			STATUS current
			DESCRIPTION
				"Description."
			::= { priPWanConnV6Entry 15 }

		
--  1.3.6.1.4.1.37950.1.1.6.2.2.8.16.1.16
		-- 1.3.6.1.4.1.37950.1.1.6.2.2.8.16.1.16
		v6wanConnSlaveDnsIpv4S OBJECT-TYPE
			SYNTAX IpAddress
			MAX-ACCESS read-write
			STATUS current
			DESCRIPTION
				"Description."
			::= { priPWanConnV6Entry 16 }

		
--  1.3.6.1.4.1.37950.1.1.6.2.2.8.16.1.17
		-- 1.3.6.1.4.1.37950.1.1.6.2.2.8.16.1.17
		v6wanConnNatEnableS OBJECT-TYPE
			SYNTAX INTEGER
				{
				disable(0),
				enable(1)
				}
			MAX-ACCESS read-write
			STATUS current
			DESCRIPTION
				"Description."
			::= { priPWanConnV6Entry 17 }

		
--  1.3.6.1.4.1.37950.1.1.6.2.2.8.16.1.18
		-- 1.3.6.1.4.1.37950.1.1.6.2.2.8.16.1.18
		v6wanConnAddressIpv6S OBJECT-TYPE
			SYNTAX OCTET STRING
			MAX-ACCESS read-write
			STATUS current
			DESCRIPTION
				"Description."
			::= { priPWanConnV6Entry 18 }

		
--  1.3.6.1.4.1.37950.1.1.6.2.2.8.16.1.19
		-- 1.3.6.1.4.1.37950.1.1.6.2.2.8.16.1.19
		v6wanConnPrefixLenIpv6S OBJECT-TYPE
			SYNTAX INTEGER (0..128)
			MAX-ACCESS read-write
			STATUS current
			DESCRIPTION
				"Description."
			::= { priPWanConnV6Entry 19 }

		
--  1.3.6.1.4.1.37950.1.1.6.2.2.8.16.1.20
		-- 1.3.6.1.4.1.37950.1.1.6.2.2.8.16.1.20
		v6wanConnGatewayIpv6S OBJECT-TYPE
			SYNTAX OCTET STRING
			MAX-ACCESS read-write
			STATUS current
			DESCRIPTION
				"Description."
			::= { priPWanConnV6Entry 20 }

		
--  1.3.6.1.4.1.37950.1.1.6.2.2.8.16.1.21
		-- 1.3.6.1.4.1.37950.1.1.6.2.2.8.16.1.21
		v6wanConnDnsEnableIpv6S OBJECT-TYPE
			SYNTAX INTEGER
				{
				disable(0),
				enable(1)
				}
			MAX-ACCESS read-write
			STATUS current
			DESCRIPTION
				"Description."
			::= { priPWanConnV6Entry 21 }

		
--  1.3.6.1.4.1.37950.1.1.6.2.2.8.16.1.22
		-- 1.3.6.1.4.1.37950.1.1.6.2.2.8.16.1.22
		v6wanConnMsaterDnsIpv6S OBJECT-TYPE
			SYNTAX OCTET STRING
			MAX-ACCESS read-write
			STATUS current
			DESCRIPTION
				"Description."
			::= { priPWanConnV6Entry 22 }

		
--  1.3.6.1.4.1.37950.1.1.6.2.2.8.16.1.23
		-- 1.3.6.1.4.1.37950.1.1.6.2.2.8.16.1.23
		v6wanConnSlaveDnsIpv6S OBJECT-TYPE
			SYNTAX OCTET STRING
			MAX-ACCESS read-write
			STATUS current
			DESCRIPTION
				"Description."
			::= { priPWanConnV6Entry 23 }

		
--  1.3.6.1.4.1.37950.1.1.6.2.2.8.16.1.24
		-- 1.3.6.1.4.1.37950.1.1.6.2.2.8.16.1.24
		v6wanConnSlaacS OBJECT-TYPE
			SYNTAX INTEGER
				{
				disable(0),
				enable(1)
				}
			MAX-ACCESS read-write
			STATUS current
			DESCRIPTION
				"Description."
			::= { priPWanConnV6Entry 24 }

		
--  1.3.6.1.4.1.37950.1.1.6.2.2.8.16.1.25
		-- 1.3.6.1.4.1.37950.1.1.6.2.2.8.16.1.25
		v6wanConnPppoeProxyS OBJECT-TYPE
			SYNTAX INTEGER
				{
				disable(0),
				enable(1)
				}
			MAX-ACCESS read-write
			STATUS current
			DESCRIPTION
				"Description."
			::= { priPWanConnV6Entry 25 }

		
--  1.3.6.1.4.1.37950.1.1.6.2.2.8.16.1.26
		-- 1.3.6.1.4.1.37950.1.1.6.2.2.8.16.1.26
		v6wanConnPppoeUsernameS OBJECT-TYPE
			SYNTAX OCTET STRING
			MAX-ACCESS read-write
			STATUS current
			DESCRIPTION
				"Description."
			::= { priPWanConnV6Entry 26 }

		
--  1.3.6.1.4.1.37950.1.1.6.2.2.8.16.1.27
		-- 1.3.6.1.4.1.37950.1.1.6.2.2.8.16.1.27
		v6wanConnPppoePasswordS OBJECT-TYPE
			SYNTAX OCTET STRING
			MAX-ACCESS read-write
			STATUS current
			DESCRIPTION
				"Description."
			::= { priPWanConnV6Entry 27 }

		
--  1.3.6.1.4.1.37950.1.1.6.2.2.8.16.1.28
		-- 1.3.6.1.4.1.37950.1.1.6.2.2.8.16.1.28
		v6wanConnPppoeSerNameS OBJECT-TYPE
			SYNTAX OCTET STRING
			MAX-ACCESS read-write
			STATUS current
			DESCRIPTION
				"Description."
			::= { priPWanConnV6Entry 28 }

		
--  1.3.6.1.4.1.37950.1.1.6.2.2.8.16.1.29
		-- 1.3.6.1.4.1.37950.1.1.6.2.2.8.16.1.29
		v6wanConnPppoeModeS OBJECT-TYPE
			SYNTAX INTEGER
				{
				autoConnect(0),
				flowConnect(1)
				}
			MAX-ACCESS read-write
			STATUS current
			DESCRIPTION
				"Description."
			::= { priPWanConnV6Entry 29 }

		
--  1.3.6.1.4.1.37950.1.1.6.2.2.8.16.1.30
		-- 1.3.6.1.4.1.37950.1.1.6.2.2.8.16.1.30
		v6wanConnDhcpv6ClientAddressS OBJECT-TYPE
			SYNTAX INTEGER
				{
				disable(0),
				enable(1)
				}
			MAX-ACCESS read-write
			STATUS current
			DESCRIPTION
				"Description."
			::= { priPWanConnV6Entry 30 }

		
--  1.3.6.1.4.1.37950.1.1.6.2.2.8.16.1.31
		-- 1.3.6.1.4.1.37950.1.1.6.2.2.8.16.1.31
		v6wanConnDhcpv6ClientPrefixS OBJECT-TYPE
			SYNTAX INTEGER
				{
				disable(0),
				enable(1)
				}
			MAX-ACCESS read-write
			STATUS current
			DESCRIPTION
				"Description."
			::= { priPWanConnV6Entry 31 }

		
--  1.3.6.1.4.1.37950.1.1.6.2.2.8.16.1.32
		-- 1.3.6.1.4.1.37950.1.1.6.2.2.8.16.1.32
		v6wanConnDsLiteEnableS OBJECT-TYPE
			SYNTAX INTEGER
				{
				disable(0),
				enable(1)
				}
			MAX-ACCESS read-write
			STATUS current
			DESCRIPTION
				"Description."
			::= { priPWanConnV6Entry 32 }

		
--  1.3.6.1.4.1.37950.1.1.6.2.2.8.16.1.33
		-- 1.3.6.1.4.1.37950.1.1.6.2.2.8.16.1.33
		v6wanConnDsLiteAftrModeS OBJECT-TYPE
			SYNTAX INTEGER
				{
				dhcpv6(0),
				manual(1)
				}
			MAX-ACCESS read-write
			STATUS current
			DESCRIPTION
				"Description."
			::= { priPWanConnV6Entry 33 }

		
--  1.3.6.1.4.1.37950.1.1.6.2.2.8.16.1.34
		-- 1.3.6.1.4.1.37950.1.1.6.2.2.8.16.1.34
		v6wanConnDsLiteAddressTypeS OBJECT-TYPE
			SYNTAX INTEGER
				{
				ipv6(0),
				dns(1)
				}
			MAX-ACCESS read-write
			STATUS current
			DESCRIPTION
				"Description."
			::= { priPWanConnV6Entry 34 }

		
--  1.3.6.1.4.1.37950.1.1.6.2.2.8.16.1.35
		-- 1.3.6.1.4.1.37950.1.1.6.2.2.8.16.1.35
		v6wanConnDsLiteAddressS OBJECT-TYPE
			SYNTAX OCTET STRING
			MAX-ACCESS read-write
			STATUS current
			DESCRIPTION
				"Description."
			::= { priPWanConnV6Entry 35 }

		
--  1.3.6.1.4.1.37950.1.1.6.2.2.8.16.1.36
		-- 1.3.6.1.4.1.37950.1.1.6.2.2.8.16.1.36
		v6wanConnQosEnableS OBJECT-TYPE
			SYNTAX INTEGER
				{
				disable(0),
				enable(1)
				}
			MAX-ACCESS read-write
			STATUS current
			DESCRIPTION
				"Description."
			::= { priPWanConnV6Entry 36 }

		
--  1.3.6.1.4.1.37950.1.1.6.2.2.8.16.1.37
		-- 1.3.6.1.4.1.37950.1.1.6.2.2.8.16.1.37
		v6wanConnVlanModeS OBJECT-TYPE
			SYNTAX INTEGER
				{
				disable(0),
				tag(1),
				transparent(2)
				}
			MAX-ACCESS read-write
			STATUS current
			DESCRIPTION
				"Description."
			::= { priPWanConnV6Entry 37 }

		
--  1.3.6.1.4.1.37950.1.1.6.2.2.8.16.1.38
		-- 1.3.6.1.4.1.37950.1.1.6.2.2.8.16.1.38
		v6wanConnTranslationEnableS OBJECT-TYPE
			SYNTAX INTEGER
				{
				disable(0),
				enable(1)
				}
			MAX-ACCESS read-write
			STATUS current
			DESCRIPTION
				"Description."
			::= { priPWanConnV6Entry 38 }

		
--  1.3.6.1.4.1.37950.1.1.6.2.2.8.16.1.39
		-- 1.3.6.1.4.1.37950.1.1.6.2.2.8.16.1.39
		v6wanConnTranslationVlanS OBJECT-TYPE
			SYNTAX INTEGER (1..4095)
			MAX-ACCESS read-write
			STATUS current
			DESCRIPTION
				"Description."
			::= { priPWanConnV6Entry 39 }

		
--  1.3.6.1.4.1.37950.1.1.6.2.2.8.16.1.40
		-- 1.3.6.1.4.1.37950.1.1.6.2.2.8.16.1.40
		v6wanConnTranslationCosS OBJECT-TYPE
			SYNTAX INTEGER (0..7)
			MAX-ACCESS read-write
			STATUS current
			DESCRIPTION
				"Description."
			::= { priPWanConnV6Entry 40 }

		
--  1.3.6.1.4.1.37950.1.1.6.2.2.8.16.1.41
		-- 1.3.6.1.4.1.37950.1.1.6.2.2.8.16.1.41
		v6wanConnQinqEnableS OBJECT-TYPE
			SYNTAX INTEGER
				{
				disable(0),
				enable(1)
				}
			MAX-ACCESS read-write
			STATUS current
			DESCRIPTION
				"Description."
			::= { priPWanConnV6Entry 41 }

		
--  1.3.6.1.4.1.37950.1.1.6.2.2.8.16.1.42
		-- 1.3.6.1.4.1.37950.1.1.6.2.2.8.16.1.42
		v6wanConnQinqTpidS OBJECT-TYPE
			SYNTAX INTEGER (1..65534)
			MAX-ACCESS read-write
			STATUS current
			DESCRIPTION
				"Description."
			::= { priPWanConnV6Entry 42 }

		
--  1.3.6.1.4.1.37950.1.1.6.2.2.8.16.1.43
		-- 1.3.6.1.4.1.37950.1.1.6.2.2.8.16.1.43
		v6wanConnSvlanIdS OBJECT-TYPE
			SYNTAX INTEGER (1..4095)
			MAX-ACCESS read-write
			STATUS current
			DESCRIPTION
				"Description."
			::= { priPWanConnV6Entry 43 }

		
--  1.3.6.1.4.1.37950.1.1.6.2.2.8.16.1.44
		-- 1.3.6.1.4.1.37950.1.1.6.2.2.8.16.1.44
		v6wanConnSvlanCosS OBJECT-TYPE
			SYNTAX INTEGER (0..7)
			MAX-ACCESS read-write
			STATUS current
			DESCRIPTION
				"Description."
			::= { priPWanConnV6Entry 44 }

		
--  1.3.6.1.4.1.37950.1.1.6.2.2.8.16.1.45
		-- 1.3.6.1.4.1.37950.1.1.6.2.2.8.16.1.45
		v6wanConnRouteMtuS OBJECT-TYPE
			SYNTAX Integer32 (0 | 576..1500)
			MAX-ACCESS read-write
			STATUS current
			DESCRIPTION
				"Description."
			::= { priPWanConnV6Entry 45 }

		
--  1.3.6.1.4.1.37950.1.1.6.2.2.8.17
		-- 1.3.6.1.4.1.37950.1.1.6.2.2.8.17
		priPDhcpServerV6Table OBJECT-TYPE
			SYNTAX SEQUENCE OF PriPDhcpServerV6Entry
			MAX-ACCESS not-accessible
			STATUS current
			DESCRIPTION
				"Description."
			::= { v1600gPriPShow 17 }

		
--  1.3.6.1.4.1.37950.1.1.6.2.2.8.17.1
		-- 1.3.6.1.4.1.37950.1.1.6.2.2.8.17.1
		priPDhcpServerV6Entry OBJECT-TYPE
			SYNTAX PriPDhcpServerV6Entry
			MAX-ACCESS not-accessible
			STATUS current
			DESCRIPTION
				"Description."
			INDEX { priPDhcpServerV6PId }
			::= { priPDhcpServerV6Table 1 }

		
		PriPDhcpServerV6Entry ::=
			SEQUENCE { 
				priPDhcpServerV6PId
					Integer32,
				priPDhcpv6LanIp
					OCTET STRING,
				priPDhcpv6Prefixlen
					INTEGER,
				priPDhcpv6PrefixMode
					INTEGER,
				priPDhcpv6PrefixModeIp
					OCTET STRING,
				priPDhcpv6ServerEable
					INTEGER,
				priPDhcpv6Preference
					Unsigned32,
				priPDhcpv6BeginIp
					OCTET STRING,
				priPDhcpv6EndIp
					OCTET STRING,
				priPDhcpv6PoolType
					INTEGER,
				priPDhcpv6MasterDns
					OCTET STRING,
				priPDhcpv6SlaveDns
					OCTET STRING,
				priPDhcpv6Gateway
					OCTET STRING,
				priPDhcpv6RelayIp
					OCTET STRING,
				priPDhcpv6RA
					INTEGER,
				priPDhcpv6RAManage
					INTEGER,
				priPDhcpv6RAOther
					INTEGER,
				priPDhcpv6RAMaxInterval
					Integer32,
				priPDhcpv6RAMinInterval
					Integer32,
				priPDhcpv6Valid
					Unsigned32,
				priPDhcpv6PrefixModeWanIndex
					Integer32,
				priPDhcpv6DNSMode
					INTEGER,
				priPDhcpv6DNSModeWanIndex
					Integer32
			 }

--  1.3.6.1.4.1.37950.1.1.6.2.2.8.17.1.1
		-- 1.3.6.1.4.1.37950.1.1.6.2.2.8.17.1.1
		priPDhcpServerV6PId OBJECT-TYPE
			SYNTAX Integer32
			MAX-ACCESS read-write
			STATUS current
			DESCRIPTION
				"Description."
			::= { priPDhcpServerV6Entry 1 }

		
--  1.3.6.1.4.1.37950.1.1.6.2.2.8.17.1.2
		-- 1.3.6.1.4.1.37950.1.1.6.2.2.8.17.1.2
		priPDhcpv6LanIp OBJECT-TYPE
			SYNTAX OCTET STRING
			MAX-ACCESS read-write
			STATUS current
			DESCRIPTION
				"Description."
			::= { priPDhcpServerV6Entry 2 }

		
--  1.3.6.1.4.1.37950.1.1.6.2.2.8.17.1.3
		-- 1.3.6.1.4.1.37950.1.1.6.2.2.8.17.1.3
		priPDhcpv6Prefixlen OBJECT-TYPE
			SYNTAX INTEGER
			MAX-ACCESS read-write
			STATUS current
			DESCRIPTION
				"Description."
			::= { priPDhcpServerV6Entry 3 }

		
--  1.3.6.1.4.1.37950.1.1.6.2.2.8.17.1.4
		-- 1.3.6.1.4.1.37950.1.1.6.2.2.8.17.1.4
		priPDhcpv6PrefixMode OBJECT-TYPE
			SYNTAX INTEGER
				{
				wan_delegated(0),
				static(1),
				auto(2)
				}
			MAX-ACCESS read-write
			STATUS current
			DESCRIPTION
				"Description."
			::= { priPDhcpServerV6Entry 4 }

		
--  1.3.6.1.4.1.37950.1.1.6.2.2.8.17.1.5
		-- 1.3.6.1.4.1.37950.1.1.6.2.2.8.17.1.5
		priPDhcpv6PrefixModeIp OBJECT-TYPE
			SYNTAX OCTET STRING
			MAX-ACCESS read-write
			STATUS current
			DESCRIPTION
				"Description."
			::= { priPDhcpServerV6Entry 5 }

		
--  1.3.6.1.4.1.37950.1.1.6.2.2.8.17.1.6
		-- 1.3.6.1.4.1.37950.1.1.6.2.2.8.17.1.6
		priPDhcpv6ServerEable OBJECT-TYPE
			SYNTAX INTEGER
				{
				disable(0),
				enable(1),
				relay(2)
				}
			MAX-ACCESS read-write
			STATUS current
			DESCRIPTION
				"Description."
			::= { priPDhcpServerV6Entry 6 }

		
--  1.3.6.1.4.1.37950.1.1.6.2.2.8.17.1.7
		-- 1.3.6.1.4.1.37950.1.1.6.2.2.8.17.1.7
		priPDhcpv6Preference OBJECT-TYPE
			SYNTAX Unsigned32
			MAX-ACCESS read-write
			STATUS current
			DESCRIPTION
				"Description."
			::= { priPDhcpServerV6Entry 7 }

		
--  1.3.6.1.4.1.37950.1.1.6.2.2.8.17.1.8
		-- 1.3.6.1.4.1.37950.1.1.6.2.2.8.17.1.8
		priPDhcpv6BeginIp OBJECT-TYPE
			SYNTAX OCTET STRING
			MAX-ACCESS read-write
			STATUS current
			DESCRIPTION
				"Description."
			::= { priPDhcpServerV6Entry 8 }

		
--  1.3.6.1.4.1.37950.1.1.6.2.2.8.17.1.9
		-- 1.3.6.1.4.1.37950.1.1.6.2.2.8.17.1.9
		priPDhcpv6EndIp OBJECT-TYPE
			SYNTAX OCTET STRING
			MAX-ACCESS read-write
			STATUS current
			DESCRIPTION
				"Description."
			::= { priPDhcpServerV6Entry 9 }

		
--  1.3.6.1.4.1.37950.1.1.6.2.2.8.17.1.10
		-- 1.3.6.1.4.1.37950.1.1.6.2.2.8.17.1.10
		priPDhcpv6PoolType OBJECT-TYPE
			SYNTAX INTEGER
				{
				pc(0),
				camera(1),
				stb(2),
				ip_phone(3)
				}
			MAX-ACCESS read-write
			STATUS current
			DESCRIPTION
				"Description."
			::= { priPDhcpServerV6Entry 10 }

		
--  1.3.6.1.4.1.37950.1.1.6.2.2.8.17.1.11
		-- 1.3.6.1.4.1.37950.1.1.6.2.2.8.17.1.11
		priPDhcpv6MasterDns OBJECT-TYPE
			SYNTAX OCTET STRING
			MAX-ACCESS read-write
			STATUS current
			DESCRIPTION
				"Description."
			::= { priPDhcpServerV6Entry 11 }

		
--  1.3.6.1.4.1.37950.1.1.6.2.2.8.17.1.12
		-- 1.3.6.1.4.1.37950.1.1.6.2.2.8.17.1.12
		priPDhcpv6SlaveDns OBJECT-TYPE
			SYNTAX OCTET STRING
			MAX-ACCESS read-write
			STATUS current
			DESCRIPTION
				"Description."
			::= { priPDhcpServerV6Entry 12 }

		
--  1.3.6.1.4.1.37950.1.1.6.2.2.8.17.1.13
		-- 1.3.6.1.4.1.37950.1.1.6.2.2.8.17.1.13
		priPDhcpv6Gateway OBJECT-TYPE
			SYNTAX OCTET STRING
			MAX-ACCESS read-write
			STATUS current
			DESCRIPTION
				"Description."
			::= { priPDhcpServerV6Entry 13 }

		
--  1.3.6.1.4.1.37950.1.1.6.2.2.8.17.1.14
		-- 1.3.6.1.4.1.37950.1.1.6.2.2.8.17.1.14
		priPDhcpv6RelayIp OBJECT-TYPE
			SYNTAX OCTET STRING
			MAX-ACCESS read-write
			STATUS current
			DESCRIPTION
				"Description."
			::= { priPDhcpServerV6Entry 14 }

		
--  1.3.6.1.4.1.37950.1.1.6.2.2.8.17.1.15
		-- 1.3.6.1.4.1.37950.1.1.6.2.2.8.17.1.15
		priPDhcpv6RA OBJECT-TYPE
			SYNTAX INTEGER
				{
				disable(0),
				enable(1)
				}
			MAX-ACCESS read-write
			STATUS current
			DESCRIPTION
				"Description."
			::= { priPDhcpServerV6Entry 15 }

		
--  1.3.6.1.4.1.37950.1.1.6.2.2.8.17.1.16
		-- 1.3.6.1.4.1.37950.1.1.6.2.2.8.17.1.16
		priPDhcpv6RAManage OBJECT-TYPE
			SYNTAX INTEGER
				{
				disable(0),
				enable(1)
				}
			MAX-ACCESS read-write
			STATUS current
			DESCRIPTION
				"Description."
			::= { priPDhcpServerV6Entry 16 }

		
--  1.3.6.1.4.1.37950.1.1.6.2.2.8.17.1.17
		-- 1.3.6.1.4.1.37950.1.1.6.2.2.8.17.1.17
		priPDhcpv6RAOther OBJECT-TYPE
			SYNTAX INTEGER
				{
				disable(0),
				enable(1)
				}
			MAX-ACCESS read-write
			STATUS current
			DESCRIPTION
				"Description."
			::= { priPDhcpServerV6Entry 17 }

		
--  1.3.6.1.4.1.37950.1.1.6.2.2.8.17.1.18
		-- 1.3.6.1.4.1.37950.1.1.6.2.2.8.17.1.18
		priPDhcpv6RAMaxInterval OBJECT-TYPE
			SYNTAX Integer32
			MAX-ACCESS read-write
			STATUS current
			DESCRIPTION
				"Description."
			::= { priPDhcpServerV6Entry 18 }

		
--  1.3.6.1.4.1.37950.1.1.6.2.2.8.17.1.19
		-- 1.3.6.1.4.1.37950.1.1.6.2.2.8.17.1.19
		priPDhcpv6RAMinInterval OBJECT-TYPE
			SYNTAX Integer32
			MAX-ACCESS read-write
			STATUS current
			DESCRIPTION
				"Description."
			::= { priPDhcpServerV6Entry 19 }

		
--  1.3.6.1.4.1.37950.1.1.6.2.2.8.17.1.20
		-- 1.3.6.1.4.1.37950.1.1.6.2.2.8.17.1.20
		priPDhcpv6Valid OBJECT-TYPE
			SYNTAX Unsigned32
			MAX-ACCESS read-write
			STATUS current
			DESCRIPTION
				"Description."
			::= { priPDhcpServerV6Entry 20 }

		
--  1.3.6.1.4.1.37950.1.1.6.2.2.8.17.1.21
		-- 1.3.6.1.4.1.37950.1.1.6.2.2.8.17.1.21
		priPDhcpv6PrefixModeWanIndex OBJECT-TYPE
			SYNTAX Integer32
			MAX-ACCESS read-write
			STATUS current
			DESCRIPTION
				"Description."
			::= { priPDhcpServerV6Entry 21 }

		
--  1.3.6.1.4.1.37950.1.1.6.2.2.8.17.1.22
		-- 1.3.6.1.4.1.37950.1.1.6.2.2.8.17.1.22
		priPDhcpv6DNSMode OBJECT-TYPE
			SYNTAX INTEGER
				{
				wanconnection(0),
				static(1),
				hgwproxy(2)
				}
			MAX-ACCESS read-write
			STATUS current
			DESCRIPTION
				"Description."
			::= { priPDhcpServerV6Entry 22 }

		
--  1.3.6.1.4.1.37950.1.1.6.2.2.8.17.1.23
		-- 1.3.6.1.4.1.37950.1.1.6.2.2.8.17.1.23
		priPDhcpv6DNSModeWanIndex OBJECT-TYPE
			SYNTAX Integer32
			MAX-ACCESS read-write
			STATUS current
			DESCRIPTION
				"Description."
			::= { priPDhcpServerV6Entry 23 }

		
--  1.3.6.1.4.1.37950.1.1.6.2.2.8.18
		-- 1.3.6.1.4.1.37950.1.1.6.2.2.8.18
		priPLoopChkTable OBJECT-TYPE
			SYNTAX SEQUENCE OF PriPLoopChkEntry
			MAX-ACCESS not-accessible
			STATUS current
			DESCRIPTION
				"Description."
			::= { v1600gPriPShow 18 }

		
--  1.3.6.1.4.1.37950.1.1.6.2.2.8.18.1
		-- 1.3.6.1.4.1.37950.1.1.6.2.2.8.18.1
		priPLoopChkEntry OBJECT-TYPE
			SYNTAX PriPLoopChkEntry
			MAX-ACCESS not-accessible
			STATUS current
			DESCRIPTION
				"Description."
			INDEX { priPLCProfileIDS }
			::= { priPLoopChkTable 1 }

		
		PriPLoopChkEntry ::=
			SEQUENCE { 
				priPLCProfileIDS
					Integer32,
				priPLCStatusS
					INTEGER,
				priPLCCheckIntervalS
					Integer32,
				priPLCRecoverIntervalS
					Integer32,
				priPLCEthernetTypeS
					OCTET STRING,
				priPLCVlanS
					Integer32,
				priPLCDestMacTypeS
					INTEGER,
				priPLCPortClosingTimeS
					Integer32,
				priPLCAlarmS
					INTEGER,
				priPLCPortdisloopedS
					INTEGER
			 }

--  1.3.6.1.4.1.37950.1.1.6.2.2.8.18.1.1
		-- 1.3.6.1.4.1.37950.1.1.6.2.2.8.18.1.1
		priPLCProfileIDS OBJECT-TYPE
			SYNTAX Integer32
			MAX-ACCESS read-write
			STATUS current
			DESCRIPTION
				"Description."
			::= { priPLoopChkEntry 1 }

		
--  1.3.6.1.4.1.37950.1.1.6.2.2.8.18.1.2
		-- 1.3.6.1.4.1.37950.1.1.6.2.2.8.18.1.2
		priPLCStatusS OBJECT-TYPE
			SYNTAX INTEGER
				{
				disable(0),
				enable(1)
				}
			MAX-ACCESS read-write
			STATUS current
			DESCRIPTION
				"Description."
			::= { priPLoopChkEntry 2 }

		
--  1.3.6.1.4.1.37950.1.1.6.2.2.8.18.1.3
		-- 1.3.6.1.4.1.37950.1.1.6.2.2.8.18.1.3
		priPLCCheckIntervalS OBJECT-TYPE
			SYNTAX Integer32
			MAX-ACCESS read-write
			STATUS current
			DESCRIPTION
				"Description."
			::= { priPLoopChkEntry 3 }

		
--  1.3.6.1.4.1.37950.1.1.6.2.2.8.18.1.4
		-- 1.3.6.1.4.1.37950.1.1.6.2.2.8.18.1.4
		priPLCRecoverIntervalS OBJECT-TYPE
			SYNTAX Integer32
			MAX-ACCESS read-write
			STATUS current
			DESCRIPTION
				"Description."
			::= { priPLoopChkEntry 4 }

		
--  1.3.6.1.4.1.37950.1.1.6.2.2.8.18.1.5
		-- 1.3.6.1.4.1.37950.1.1.6.2.2.8.18.1.5
		priPLCEthernetTypeS OBJECT-TYPE
			SYNTAX OCTET STRING
			MAX-ACCESS read-write
			STATUS current
			DESCRIPTION
				"Description."
			::= { priPLoopChkEntry 5 }

		
--  1.3.6.1.4.1.37950.1.1.6.2.2.8.18.1.6
		-- 1.3.6.1.4.1.37950.1.1.6.2.2.8.18.1.6
		priPLCVlanS OBJECT-TYPE
			SYNTAX Integer32
			MAX-ACCESS read-write
			STATUS current
			DESCRIPTION
				"Description."
			::= { priPLoopChkEntry 6 }

		
--  1.3.6.1.4.1.37950.1.1.6.2.2.8.18.1.7
		-- 1.3.6.1.4.1.37950.1.1.6.2.2.8.18.1.7
		priPLCDestMacTypeS OBJECT-TYPE
			SYNTAX INTEGER
				{
				broadcast_address(0),
				bpdu_address(1)
				}
			MAX-ACCESS read-write
			STATUS current
			DESCRIPTION
				"Description."
			::= { priPLoopChkEntry 7 }

		
--  1.3.6.1.4.1.37950.1.1.6.2.2.8.18.1.8
		-- 1.3.6.1.4.1.37950.1.1.6.2.2.8.18.1.8
		priPLCPortClosingTimeS OBJECT-TYPE
			SYNTAX Integer32
			MAX-ACCESS read-write
			STATUS current
			DESCRIPTION
				"Description."
			::= { priPLoopChkEntry 8 }

		
--  1.3.6.1.4.1.37950.1.1.6.2.2.8.18.1.9
		-- 1.3.6.1.4.1.37950.1.1.6.2.2.8.18.1.9
		priPLCAlarmS OBJECT-TYPE
			SYNTAX INTEGER
				{
				disable(0),
				enable(1)
				}
			MAX-ACCESS read-write
			STATUS current
			DESCRIPTION
				"Description."
			::= { priPLoopChkEntry 9 }

		
--  1.3.6.1.4.1.37950.1.1.6.2.2.8.18.1.10
		-- 1.3.6.1.4.1.37950.1.1.6.2.2.8.18.1.10
		priPLCPortdisloopedS OBJECT-TYPE
			SYNTAX INTEGER
				{
				disable(0),
				enable(1)
				}
			MAX-ACCESS read-write
			STATUS current
			DESCRIPTION
				"Description."
			::= { priPLoopChkEntry 10 }

		
--  1.3.6.1.4.1.37950.1.1.6.2.2.8.19
		-- 1.3.6.1.4.1.37950.1.1.6.2.2.8.19
		priPTr069ManageTable OBJECT-TYPE
			SYNTAX SEQUENCE OF PriPTr069ManageEntry
			MAX-ACCESS not-accessible
			STATUS current
			DESCRIPTION
				"Description."
			::= { v1600gPriPShow 19 }

		
--  1.3.6.1.4.1.37950.1.1.6.2.2.8.19.1
		-- 1.3.6.1.4.1.37950.1.1.6.2.2.8.19.1
		priPTr069ManageEntry OBJECT-TYPE
			SYNTAX PriPTr069ManageEntry
			MAX-ACCESS not-accessible
			STATUS current
			DESCRIPTION
				"Description."
			INDEX { onuMngSrvId }
			::= { priPTr069ManageTable 1 }

		
		PriPTr069ManageEntry ::=
			SEQUENCE { 
				onuMngSrvId
					Integer32,
				onuMngAcsAddress
					OCTET STRING,
				onuMngAcsUsername
					OCTET STRING,
				onuMngAcsPassword
					OCTET STRING,
				onuMngCertificateEn
					INTEGER,
				onuMngInformEn
					INTEGER,
				onuMngInformIntervalTime
					Unsigned32,
				onuMngRevConnUsername
					OCTET STRING,
				onuMngRevConnPassword
					OCTET STRING,
				onuMngStatus
					INTEGER,
				onuMngID
					OCTET STRING
			 }

--  1.3.6.1.4.1.37950.1.1.6.2.2.8.19.1.1
		-- 1.3.6.1.4.1.37950.1.1.6.2.2.8.19.1.1
		onuMngSrvId OBJECT-TYPE
			SYNTAX Integer32
			MAX-ACCESS read-only
			STATUS current
			DESCRIPTION
				"Description."
			::= { priPTr069ManageEntry 1 }

		
--  1.3.6.1.4.1.37950.1.1.6.2.2.8.19.1.2
		-- 1.3.6.1.4.1.37950.1.1.6.2.2.8.19.1.2
		onuMngAcsAddress OBJECT-TYPE
			SYNTAX OCTET STRING
			MAX-ACCESS read-only
			STATUS current
			DESCRIPTION
				"Description."
			::= { priPTr069ManageEntry 2 }

		
--  1.3.6.1.4.1.37950.1.1.6.2.2.8.19.1.3
		-- 1.3.6.1.4.1.37950.1.1.6.2.2.8.19.1.3
		onuMngAcsUsername OBJECT-TYPE
			SYNTAX OCTET STRING
			MAX-ACCESS read-only
			STATUS current
			DESCRIPTION
				"Description."
			::= { priPTr069ManageEntry 3 }

		
--  1.3.6.1.4.1.37950.1.1.6.2.2.8.19.1.4
		-- 1.3.6.1.4.1.37950.1.1.6.2.2.8.19.1.4
		onuMngAcsPassword OBJECT-TYPE
			SYNTAX OCTET STRING
			MAX-ACCESS read-only
			STATUS current
			DESCRIPTION
				"Description."
			::= { priPTr069ManageEntry 4 }

		
--  1.3.6.1.4.1.37950.1.1.6.2.2.8.19.1.5
		-- 1.3.6.1.4.1.37950.1.1.6.2.2.8.19.1.5
		onuMngCertificateEn OBJECT-TYPE
			SYNTAX INTEGER
				{
				disable(0),
				enable(1)
				}
			MAX-ACCESS read-only
			STATUS current
			DESCRIPTION
				"Description."
			::= { priPTr069ManageEntry 5 }

		
--  1.3.6.1.4.1.37950.1.1.6.2.2.8.19.1.6
		-- 1.3.6.1.4.1.37950.1.1.6.2.2.8.19.1.6
		onuMngInformEn OBJECT-TYPE
			SYNTAX INTEGER
				{
				disable(0),
				enable(1)
				}
			MAX-ACCESS read-only
			STATUS current
			DESCRIPTION
				"Description."
			::= { priPTr069ManageEntry 6 }

		
--  1.3.6.1.4.1.37950.1.1.6.2.2.8.19.1.7
		-- 1.3.6.1.4.1.37950.1.1.6.2.2.8.19.1.7
		onuMngInformIntervalTime OBJECT-TYPE
			SYNTAX Unsigned32
			MAX-ACCESS read-only
			STATUS current
			DESCRIPTION
				"Description."
			::= { priPTr069ManageEntry 7 }

		
--  1.3.6.1.4.1.37950.1.1.6.2.2.8.19.1.8
		-- 1.3.6.1.4.1.37950.1.1.6.2.2.8.19.1.8
		onuMngRevConnUsername OBJECT-TYPE
			SYNTAX OCTET STRING
			MAX-ACCESS read-only
			STATUS current
			DESCRIPTION
				"Description."
			::= { priPTr069ManageEntry 8 }

		
--  1.3.6.1.4.1.37950.1.1.6.2.2.8.19.1.9
		-- 1.3.6.1.4.1.37950.1.1.6.2.2.8.19.1.9
		onuMngRevConnPassword OBJECT-TYPE
			SYNTAX OCTET STRING
			MAX-ACCESS read-only
			STATUS current
			DESCRIPTION
				"Description."
			::= { priPTr069ManageEntry 9 }

		
--  1.3.6.1.4.1.37950.1.1.6.2.2.8.19.1.10
		-- 1.3.6.1.4.1.37950.1.1.6.2.2.8.19.1.10
		onuMngStatus OBJECT-TYPE
			SYNTAX INTEGER
				{
				disable(0),
				enable(1)
				}
			MAX-ACCESS read-only
			STATUS current
			DESCRIPTION
				"Description."
			::= { priPTr069ManageEntry 10 }

		
--  1.3.6.1.4.1.37950.1.1.6.2.2.8.19.1.11
		-- 1.3.6.1.4.1.37950.1.1.6.2.2.8.19.1.11
		onuMngID OBJECT-TYPE
			SYNTAX OCTET STRING
			MAX-ACCESS read-write
			STATUS current
			DESCRIPTION
				"Description."
			::= { priPTr069ManageEntry 11 }

		
--  1.3.6.1.4.1.37950.1.1.6.2.2.8.20
		-- 1.3.6.1.4.1.37950.1.1.6.2.2.8.20
		priPTr069StunTable OBJECT-TYPE
			SYNTAX SEQUENCE OF PriPTr069StunEntry
			MAX-ACCESS not-accessible
			STATUS current
			DESCRIPTION
				"Description."
			::= { v1600gPriPShow 20 }

		
--  1.3.6.1.4.1.37950.1.1.6.2.2.8.20.1
		-- 1.3.6.1.4.1.37950.1.1.6.2.2.8.20.1
		priPTr069StunEntry OBJECT-TYPE
			SYNTAX PriPTr069StunEntry
			MAX-ACCESS not-accessible
			STATUS current
			DESCRIPTION
				"Description."
			INDEX { onuStunSrvId }
			::= { priPTr069StunTable 1 }

		
		PriPTr069StunEntry ::=
			SEQUENCE { 
				onuStunSrvId
					Integer32,
				onuStunServerAddress
					OCTET STRING,
				onuStunServerPort
					Integer32,
				onuStunServerUsername
					OCTET STRING,
				onuStunServerPassword
					OCTET STRING,
				onuStunStatus
					INTEGER
			 }

--  1.3.6.1.4.1.37950.1.1.6.2.2.8.20.1.1
		-- 1.3.6.1.4.1.37950.1.1.6.2.2.8.20.1.1
		onuStunSrvId OBJECT-TYPE
			SYNTAX Integer32
			MAX-ACCESS read-only
			STATUS current
			DESCRIPTION
				"Description."
			::= { priPTr069StunEntry 1 }

		
--  1.3.6.1.4.1.37950.1.1.6.2.2.8.20.1.2
		-- 1.3.6.1.4.1.37950.1.1.6.2.2.8.20.1.2
		onuStunServerAddress OBJECT-TYPE
			SYNTAX OCTET STRING
			MAX-ACCESS read-only
			STATUS current
			DESCRIPTION
				"Description."
			::= { priPTr069StunEntry 2 }

		
--  1.3.6.1.4.1.37950.1.1.6.2.2.8.20.1.3
		-- 1.3.6.1.4.1.37950.1.1.6.2.2.8.20.1.3
		onuStunServerPort OBJECT-TYPE
			SYNTAX Integer32
			MAX-ACCESS read-only
			STATUS current
			DESCRIPTION
				"Description."
			::= { priPTr069StunEntry 3 }

		
--  1.3.6.1.4.1.37950.1.1.6.2.2.8.20.1.4
		-- 1.3.6.1.4.1.37950.1.1.6.2.2.8.20.1.4
		onuStunServerUsername OBJECT-TYPE
			SYNTAX OCTET STRING
			MAX-ACCESS read-only
			STATUS current
			DESCRIPTION
				"Description."
			::= { priPTr069StunEntry 4 }

		
--  1.3.6.1.4.1.37950.1.1.6.2.2.8.20.1.5
		-- 1.3.6.1.4.1.37950.1.1.6.2.2.8.20.1.5
		onuStunServerPassword OBJECT-TYPE
			SYNTAX OCTET STRING
			MAX-ACCESS read-only
			STATUS current
			DESCRIPTION
				"Description."
			::= { priPTr069StunEntry 5 }

		
--  1.3.6.1.4.1.37950.1.1.6.2.2.8.20.1.6
		-- 1.3.6.1.4.1.37950.1.1.6.2.2.8.20.1.6
		onuStunStatus OBJECT-TYPE
			SYNTAX INTEGER
				{
				disable(0),
				enable(1)
				}
			MAX-ACCESS read-only
			STATUS current
			DESCRIPTION
				"Description."
			::= { priPTr069StunEntry 6 }

		
--  1.3.6.1.4.1.37950.1.1.6.2.2.8.21
		-- 1.3.6.1.4.1.37950.1.1.6.2.2.8.21
		priPNatTypeTable OBJECT-TYPE
			SYNTAX SEQUENCE OF PriPNatTypeEntry
			MAX-ACCESS not-accessible
			STATUS current
			DESCRIPTION
				"Description."
			::= { v1600gPriPShow 21 }

		
--  1.3.6.1.4.1.37950.1.1.6.2.2.8.21.1
		-- 1.3.6.1.4.1.37950.1.1.6.2.2.8.21.1
		priPNatTypeEntry OBJECT-TYPE
			SYNTAX PriPNatTypeEntry
			MAX-ACCESS not-accessible
			STATUS current
			DESCRIPTION
				"Description."
			INDEX { priPNatTypePIDS }
			::= { priPNatTypeTable 1 }

		
		PriPNatTypeEntry ::=
			SEQUENCE { 
				priPNatTypePIDS
					Integer32,
				natTypeS
					INTEGER
			 }

--  1.3.6.1.4.1.37950.1.1.6.2.2.8.21.1.1
		-- 1.3.6.1.4.1.37950.1.1.6.2.2.8.21.1.1
		priPNatTypePIDS OBJECT-TYPE
			SYNTAX Integer32
			MAX-ACCESS read-write
			STATUS current
			DESCRIPTION
				"Description."
			::= { priPNatTypeEntry 1 }

		
--     1.3.6.1.4.1.37950.1.1.5.12.9.2.42.1.1
-- 1.3.6.1.4.1.37950.1.1.5.12.9.2.42.1.1
-- 1.3.6.1.4.1.37950.1.1.5.12.9.2.42.1.1
-- 1.3.6.1.4.1.37950.1.1.6.2.2.8.21.1.2
		-- 1.3.6.1.4.1.37950.1.1.6.2.2.8.21.1.2
		natTypeS OBJECT-TYPE
			SYNTAX INTEGER
				{
				nat1(1),
				nat2(2),
				nat3(3),
				nat4-napt(4)
				}
			MAX-ACCESS read-write
			STATUS current
			DESCRIPTION
				"Description."
			::= { priPNatTypeEntry 2 }

		
--  1.3.6.1.4.1.37950.1.1.6.2.2.8.22
		-- 1.3.6.1.4.1.37950.1.1.6.2.2.8.22
		priPUPnPTable OBJECT-TYPE
			SYNTAX SEQUENCE OF PriPUPnPEntry
			MAX-ACCESS not-accessible
			STATUS current
			DESCRIPTION
				"Description."
			::= { v1600gPriPShow 22 }

		
--  1.3.6.1.4.1.37950.1.1.6.2.2.8.22.1
		-- 1.3.6.1.4.1.37950.1.1.6.2.2.8.22.1
		priPUPnPEntry OBJECT-TYPE
			SYNTAX PriPUPnPEntry
			MAX-ACCESS not-accessible
			STATUS current
			DESCRIPTION
				"Description."
			INDEX { priPUPnPPIDS }
			::= { priPUPnPTable 1 }

		
		PriPUPnPEntry ::=
			SEQUENCE { 
				priPUPnPPIDS
					Integer32,
				upnpStatusS
					INTEGER,
				upnpWanIndexS
					Integer32
			 }

--  1.3.6.1.4.1.37950.1.1.6.2.2.8.22.1.1
		-- 1.3.6.1.4.1.37950.1.1.6.2.2.8.22.1.1
		priPUPnPPIDS OBJECT-TYPE
			SYNTAX Integer32
			MAX-ACCESS read-write
			STATUS current
			DESCRIPTION
				"Description."
			::= { priPUPnPEntry 1 }

		
--     1.3.6.1.4.1.37950.1.1.5.12.9.2.42.1.2
-- 1.3.6.1.4.1.37950.1.1.5.12.9.2.42.1.2
-- 1.3.6.1.4.1.37950.1.1.5.12.9.2.42.1.2
-- 1.3.6.1.4.1.37950.1.1.6.2.2.8.22.1.2
		-- 1.3.6.1.4.1.37950.1.1.6.2.2.8.22.1.2
		upnpStatusS OBJECT-TYPE
			SYNTAX INTEGER
				{
				disable(0),
				enable(1)
				}
			MAX-ACCESS read-write
			STATUS current
			DESCRIPTION
				"Description."
			::= { priPUPnPEntry 2 }

		
--  1.3.6.1.4.1.37950.1.1.6.2.2.8.22.1.3
		-- 1.3.6.1.4.1.37950.1.1.6.2.2.8.22.1.3
		upnpWanIndexS OBJECT-TYPE
			SYNTAX Integer32
			MAX-ACCESS read-write
			STATUS current
			DESCRIPTION
				"Description."
			::= { priPUPnPEntry 3 }

		
--  1.3.6.1.4.1.37950.1.1.6.2.2.8.23
		-- 1.3.6.1.4.1.37950.1.1.6.2.2.8.23
		priPH248ServerTable OBJECT-TYPE
			SYNTAX SEQUENCE OF PriPH248ServerEntry
			MAX-ACCESS not-accessible
			STATUS current
			DESCRIPTION
				"Description."
			::= { v1600gPriPShow 23 }

		
--  1.3.6.1.4.1.37950.1.1.6.2.2.8.23.1
		-- 1.3.6.1.4.1.37950.1.1.6.2.2.8.23.1
		priPH248ServerEntry OBJECT-TYPE
			SYNTAX PriPH248ServerEntry
			MAX-ACCESS not-accessible
			STATUS current
			DESCRIPTION
				"Description."
			INDEX { h248SrvPIDS }
			::= { priPH248ServerTable 1 }

		
		PriPH248ServerEntry ::=
			SEQUENCE { 
				h248SrvPIDS
					Integer32,
				h248SrvMGPortS
					Integer32,
				h248SrvMGCServerS
					OCTET STRING,
				h248SrvMGCPortS
					Integer32,
				h248SrvBackupMGCServerS
					OCTET STRING,
				h248SrvBackupMGCPortS
					Integer32,
				h248SrvRegisterModeS
					INTEGER,
				h248SrvMIDS
					OCTET STRING,
				h248SrvHeartbeatModeS
					INTEGER,
				h248SrvHeartbeatFormatS
					INTEGER,
				h248SrvHeartbeatCycleS
					Integer32,
				h248SrvHeartbeatCountS
					Integer32
			 }

--  1.3.6.1.4.1.37950.1.1.6.2.2.8.23.1.1
		-- 1.3.6.1.4.1.37950.1.1.6.2.2.8.23.1.1
		h248SrvPIDS OBJECT-TYPE
			SYNTAX Integer32
			MAX-ACCESS read-write
			STATUS current
			DESCRIPTION
				"Description."
			::= { priPH248ServerEntry 1 }

		
--  1.3.6.1.4.1.37950.1.1.6.2.2.8.23.1.2
		-- 1.3.6.1.4.1.37950.1.1.6.2.2.8.23.1.2
		h248SrvMGPortS OBJECT-TYPE
			SYNTAX Integer32
			MAX-ACCESS read-write
			STATUS current
			DESCRIPTION
				"Description."
			::= { priPH248ServerEntry 2 }

		
--  1.3.6.1.4.1.37950.1.1.6.2.2.8.23.1.3
		-- 1.3.6.1.4.1.37950.1.1.6.2.2.8.23.1.3
		h248SrvMGCServerS OBJECT-TYPE
			SYNTAX OCTET STRING
			MAX-ACCESS read-write
			STATUS current
			DESCRIPTION
				"Description."
			::= { priPH248ServerEntry 3 }

		
--  1.3.6.1.4.1.37950.1.1.6.2.2.8.23.1.4
		-- 1.3.6.1.4.1.37950.1.1.6.2.2.8.23.1.4
		h248SrvMGCPortS OBJECT-TYPE
			SYNTAX Integer32
			MAX-ACCESS read-write
			STATUS current
			DESCRIPTION
				"Description."
			::= { priPH248ServerEntry 4 }

		
--  1.3.6.1.4.1.37950.1.1.6.2.2.8.23.1.5
		-- 1.3.6.1.4.1.37950.1.1.6.2.2.8.23.1.5
		h248SrvBackupMGCServerS OBJECT-TYPE
			SYNTAX OCTET STRING
			MAX-ACCESS read-write
			STATUS current
			DESCRIPTION
				"Description."
			::= { priPH248ServerEntry 5 }

		
--  1.3.6.1.4.1.37950.1.1.6.2.2.8.23.1.6
		-- 1.3.6.1.4.1.37950.1.1.6.2.2.8.23.1.6
		h248SrvBackupMGCPortS OBJECT-TYPE
			SYNTAX Integer32
			MAX-ACCESS read-write
			STATUS current
			DESCRIPTION
				"Description."
			::= { priPH248ServerEntry 6 }

		
--  1.3.6.1.4.1.37950.1.1.6.2.2.8.23.1.7
		-- 1.3.6.1.4.1.37950.1.1.6.2.2.8.23.1.7
		h248SrvRegisterModeS OBJECT-TYPE
			SYNTAX INTEGER
				{
				ip_address(0),
				domain_name(1),
				device_name(2)
				}
			MAX-ACCESS read-write
			STATUS current
			DESCRIPTION
				"Description."
			::= { priPH248ServerEntry 7 }

		
--  1.3.6.1.4.1.37950.1.1.6.2.2.8.23.1.8
		-- 1.3.6.1.4.1.37950.1.1.6.2.2.8.23.1.8
		h248SrvMIDS OBJECT-TYPE
			SYNTAX OCTET STRING
			MAX-ACCESS read-write
			STATUS current
			DESCRIPTION
				"Description."
			::= { priPH248ServerEntry 8 }

		
--  1.3.6.1.4.1.37950.1.1.6.2.2.8.23.1.9
		-- 1.3.6.1.4.1.37950.1.1.6.2.2.8.23.1.9
		h248SrvHeartbeatModeS OBJECT-TYPE
			SYNTAX INTEGER
				{
				disable(0),
				active_enable(1),
				passive_enable(2)
				}
			MAX-ACCESS read-write
			STATUS current
			DESCRIPTION
				"Description."
			::= { priPH248ServerEntry 9 }

		
--  1.3.6.1.4.1.37950.1.1.6.2.2.8.23.1.10
		-- 1.3.6.1.4.1.37950.1.1.6.2.2.8.23.1.10
		h248SrvHeartbeatFormatS OBJECT-TYPE
			SYNTAX INTEGER
				{
				notify(1),
				service_change(2)
				}
			MAX-ACCESS read-write
			STATUS current
			DESCRIPTION
				"Description."
			::= { priPH248ServerEntry 10 }

		
--  1.3.6.1.4.1.37950.1.1.6.2.2.8.23.1.11
		-- 1.3.6.1.4.1.37950.1.1.6.2.2.8.23.1.11
		h248SrvHeartbeatCycleS OBJECT-TYPE
			SYNTAX Integer32
			MAX-ACCESS read-write
			STATUS current
			DESCRIPTION
				"Description."
			::= { priPH248ServerEntry 11 }

		
--  1.3.6.1.4.1.37950.1.1.6.2.2.8.23.1.12
		-- 1.3.6.1.4.1.37950.1.1.6.2.2.8.23.1.12
		h248SrvHeartbeatCountS OBJECT-TYPE
			SYNTAX Integer32
			MAX-ACCESS read-write
			STATUS current
			DESCRIPTION
				"Description."
			::= { priPH248ServerEntry 12 }

		
--  1.3.6.1.4.1.37950.1.1.6.2.2.8.24
		-- 1.3.6.1.4.1.37950.1.1.6.2.2.8.24
		priPH248UserTable OBJECT-TYPE
			SYNTAX SEQUENCE OF PriPH248UserEntry
			MAX-ACCESS not-accessible
			STATUS current
			DESCRIPTION
				"Description."
			::= { v1600gPriPShow 24 }

		
--  1.3.6.1.4.1.37950.1.1.6.2.2.8.24.1
		-- 1.3.6.1.4.1.37950.1.1.6.2.2.8.24.1
		priPH248UserEntry OBJECT-TYPE
			SYNTAX PriPH248UserEntry
			MAX-ACCESS not-accessible
			STATUS current
			DESCRIPTION
				"Description."
			INDEX { h248UserPIDS, h248UserPortIndexS }
			::= { priPH248UserTable 1 }

		
		PriPH248UserEntry ::=
			SEQUENCE { 
				h248UserPIDS
					Integer32,
				h248UserPortIndexS
					Integer32,
				h248UserNameS
					OCTET STRING
			 }

--  1.3.6.1.4.1.37950.1.1.6.2.2.8.24.1.1
		-- 1.3.6.1.4.1.37950.1.1.6.2.2.8.24.1.1
		h248UserPIDS OBJECT-TYPE
			SYNTAX Integer32
			MAX-ACCESS read-write
			STATUS current
			DESCRIPTION
				"Description."
			::= { priPH248UserEntry 1 }

		
--  1.3.6.1.4.1.37950.1.1.6.2.2.8.24.1.2
		-- 1.3.6.1.4.1.37950.1.1.6.2.2.8.24.1.2
		h248UserPortIndexS OBJECT-TYPE
			SYNTAX Integer32
			MAX-ACCESS read-write
			STATUS current
			DESCRIPTION
				"Description."
			::= { priPH248UserEntry 2 }

		
--  1.3.6.1.4.1.37950.1.1.6.2.2.8.24.1.3
		-- 1.3.6.1.4.1.37950.1.1.6.2.2.8.24.1.3
		h248UserNameS OBJECT-TYPE
			SYNTAX OCTET STRING
			MAX-ACCESS read-write
			STATUS current
			DESCRIPTION
				"Description."
			::= { priPH248UserEntry 3 }

		
--  1.3.6.1.4.1.37950.1.1.6.2.2.8.25
		-- 1.3.6.1.4.1.37950.1.1.6.2.2.8.25
		priPH248SignalMediaAloneTable OBJECT-TYPE
			SYNTAX SEQUENCE OF PriPH248SignalMediaAloneEntry
			MAX-ACCESS not-accessible
			STATUS current
			DESCRIPTION
				"Description."
			::= { v1600gPriPShow 25 }

		
--  1.3.6.1.4.1.37950.1.1.6.2.2.8.25.1
		-- 1.3.6.1.4.1.37950.1.1.6.2.2.8.25.1
		priPH248SignalMediaAloneEntry OBJECT-TYPE
			SYNTAX PriPH248SignalMediaAloneEntry
			MAX-ACCESS not-accessible
			STATUS current
			DESCRIPTION
				"Description."
			INDEX { priPH248SMAPIDS }
			::= { priPH248SignalMediaAloneTable 1 }

		
		PriPH248SignalMediaAloneEntry ::=
			SEQUENCE { 
				priPH248SMAPIDS
					Integer32,
				priPH248SMAStatusS
					INTEGER,
				priPH248SMAWanIndexS
					Integer32
			 }

--  1.3.6.1.4.1.37950.1.1.6.2.2.8.25.1.1
		-- 1.3.6.1.4.1.37950.1.1.6.2.2.8.25.1.1
		priPH248SMAPIDS OBJECT-TYPE
			SYNTAX Integer32
			MAX-ACCESS read-write
			STATUS current
			DESCRIPTION
				"Description."
			::= { priPH248SignalMediaAloneEntry 1 }

		
--  1.3.6.1.4.1.37950.1.1.6.2.2.8.25.1.2
		-- 1.3.6.1.4.1.37950.1.1.6.2.2.8.25.1.2
		priPH248SMAStatusS OBJECT-TYPE
			SYNTAX INTEGER
				{
				disable(0),
				enable(1)
				}
			MAX-ACCESS read-write
			STATUS current
			DESCRIPTION
				"Description."
			::= { priPH248SignalMediaAloneEntry 2 }

		
--  1.3.6.1.4.1.37950.1.1.6.2.2.8.25.1.3
		-- 1.3.6.1.4.1.37950.1.1.6.2.2.8.25.1.3
		priPH248SMAWanIndexS OBJECT-TYPE
			SYNTAX Integer32
			MAX-ACCESS read-write
			STATUS current
			DESCRIPTION
				"Description."
			::= { priPH248SignalMediaAloneEntry 3 }

		
--  1.3.6.1.4.1.37950.1.1.6.2.2.8.26
		-- 1.3.6.1.4.1.37950.1.1.6.2.2.8.26
		priPMacAclRuleTable OBJECT-TYPE
			SYNTAX SEQUENCE OF PriPMacAclRuleEntry
			MAX-ACCESS not-accessible
			STATUS current
			DESCRIPTION
				"Description."
			::= { v1600gPriPShow 26 }

		
--  1.3.6.1.4.1.37950.1.1.6.2.2.8.26.1
		-- 1.3.6.1.4.1.37950.1.1.6.2.2.8.26.1
		priPMacAclRuleEntry OBJECT-TYPE
			SYNTAX PriPMacAclRuleEntry
			MAX-ACCESS not-accessible
			STATUS current
			DESCRIPTION
				"Description."
			INDEX { priPMRulePIDS }
			::= { priPMacAclRuleTable 1 }

		
		PriPMacAclRuleEntry ::=
			SEQUENCE { 
				priPMRulePIDS
					Integer32,
				priPMRuleStatusS
					INTEGER,
				priPMRuleModeS
					INTEGER
			 }

--  1.3.6.1.4.1.37950.1.1.6.2.2.8.26.1.1
		-- 1.3.6.1.4.1.37950.1.1.6.2.2.8.26.1.1
		priPMRulePIDS OBJECT-TYPE
			SYNTAX Integer32
			MAX-ACCESS read-write
			STATUS current
			DESCRIPTION
				"Description."
			::= { priPMacAclRuleEntry 1 }

		
--  1.3.6.1.4.1.37950.1.1.6.2.2.8.26.1.2
		-- 1.3.6.1.4.1.37950.1.1.6.2.2.8.26.1.2
		priPMRuleStatusS OBJECT-TYPE
			SYNTAX INTEGER
				{
				disable(0),
				enable(1)
				}
			MAX-ACCESS read-write
			STATUS current
			DESCRIPTION
				"Description."
			::= { priPMacAclRuleEntry 2 }

		
--  1.3.6.1.4.1.37950.1.1.6.2.2.8.26.1.3
		-- 1.3.6.1.4.1.37950.1.1.6.2.2.8.26.1.3
		priPMRuleModeS OBJECT-TYPE
			SYNTAX INTEGER { whitelist(0) }
			MAX-ACCESS read-write
			STATUS current
			DESCRIPTION
				"Description."
			::= { priPMacAclRuleEntry 3 }

		
--  1.3.6.1.4.1.37950.1.1.6.2.2.8.27
		-- 1.3.6.1.4.1.37950.1.1.6.2.2.8.27
		priPMacAclGroupTable OBJECT-TYPE
			SYNTAX SEQUENCE OF PriPMacAclGroupEntry
			MAX-ACCESS not-accessible
			STATUS current
			DESCRIPTION
				"Description."
			::= { v1600gPriPShow 27 }

		
--  1.3.6.1.4.1.37950.1.1.6.2.2.8.27.1
		-- 1.3.6.1.4.1.37950.1.1.6.2.2.8.27.1
		priPMacAclGroupEntry OBJECT-TYPE
			SYNTAX PriPMacAclGroupEntry
			MAX-ACCESS not-accessible
			STATUS current
			DESCRIPTION
				"Description."
			INDEX { priPMGroupPIDS, priPMGroupGroupNumS }
			::= { priPMacAclGroupTable 1 }

		
		PriPMacAclGroupEntry ::=
			SEQUENCE { 
				priPMGroupPIDS
					Integer32,
				priPMGroupGroupNumS
					Integer32,
				priPMGroupMACS
					OCTET STRING,
				priPMGroupMaskS
					OCTET STRING
			 }

--  1.3.6.1.4.1.37950.1.1.6.2.2.8.27.1.1
		-- 1.3.6.1.4.1.37950.1.1.6.2.2.8.27.1.1
		priPMGroupPIDS OBJECT-TYPE
			SYNTAX Integer32
			MAX-ACCESS read-write
			STATUS current
			DESCRIPTION
				"Description."
			::= { priPMacAclGroupEntry 1 }

		
--  1.3.6.1.4.1.37950.1.1.6.2.2.8.27.1.2
		-- 1.3.6.1.4.1.37950.1.1.6.2.2.8.27.1.2
		priPMGroupGroupNumS OBJECT-TYPE
			SYNTAX Integer32
			MAX-ACCESS read-write
			STATUS current
			DESCRIPTION
				"Description."
			::= { priPMacAclGroupEntry 2 }

		
--  1.3.6.1.4.1.37950.1.1.6.2.2.8.27.1.3
		-- 1.3.6.1.4.1.37950.1.1.6.2.2.8.27.1.3
		priPMGroupMACS OBJECT-TYPE
			SYNTAX OCTET STRING
			MAX-ACCESS read-write
			STATUS current
			DESCRIPTION
				"Description."
			::= { priPMacAclGroupEntry 3 }

		
--  1.3.6.1.4.1.37950.1.1.6.2.2.8.27.1.4
		-- 1.3.6.1.4.1.37950.1.1.6.2.2.8.27.1.4
		priPMGroupMaskS OBJECT-TYPE
			SYNTAX OCTET STRING
			MAX-ACCESS read-write
			STATUS current
			DESCRIPTION
				"Description."
			::= { priPMacAclGroupEntry 4 }

		
--  1.3.6.1.4.1.37950.1.1.6.2.2.8.28
		-- 1.3.6.1.4.1.37950.1.1.6.2.2.8.28
		priPMQTTTable OBJECT-TYPE
			SYNTAX SEQUENCE OF PriPMQTTEntry
			MAX-ACCESS not-accessible
			STATUS current
			DESCRIPTION
				"Description."
			::= { v1600gPriPShow 28 }

		
--  1.3.6.1.4.1.37950.1.1.6.2.2.8.28.1
		-- 1.3.6.1.4.1.37950.1.1.6.2.2.8.28.1
		priPMQTTEntry OBJECT-TYPE
			SYNTAX PriPMQTTEntry
			MAX-ACCESS not-accessible
			STATUS current
			DESCRIPTION
				"Description."
			INDEX { priPMQTTPIDS }
			::= { priPMQTTTable 1 }

		
		PriPMQTTEntry ::=
			SEQUENCE { 
				priPMQTTPIDS
					Integer32,
				priPMQTTEnableStatusS
					INTEGER,
				priPMQTTAddressS
					OCTET STRING,
				priPMQTTUserNameS
					OCTET STRING,
				priPMQTTPasswordS
					OCTET STRING,
				priPMQTTIDS
					OCTET STRING
			 }

--  1.3.6.1.4.1.37950.1.1.6.2.2.8.28.1.1
		-- 1.3.6.1.4.1.37950.1.1.6.2.2.8.28.1.1
		priPMQTTPIDS OBJECT-TYPE
			SYNTAX Integer32
			MAX-ACCESS read-write
			STATUS current
			DESCRIPTION
				"Description."
			::= { priPMQTTEntry 1 }

		
--  1.3.6.1.4.1.37950.1.1.6.2.2.8.28.1.2
		-- 1.3.6.1.4.1.37950.1.1.6.2.2.8.28.1.2
		priPMQTTEnableStatusS OBJECT-TYPE
			SYNTAX INTEGER
				{
				disable(0),
				enable(1)
				}
			MAX-ACCESS read-write
			STATUS current
			DESCRIPTION
				"Description."
			::= { priPMQTTEntry 2 }

		
--  1.3.6.1.4.1.37950.1.1.6.2.2.8.28.1.3
		-- 1.3.6.1.4.1.37950.1.1.6.2.2.8.28.1.3
		priPMQTTAddressS OBJECT-TYPE
			SYNTAX OCTET STRING
			MAX-ACCESS read-write
			STATUS current
			DESCRIPTION
				"Description."
			::= { priPMQTTEntry 3 }

		
--  1.3.6.1.4.1.37950.1.1.6.2.2.8.28.1.4
		-- 1.3.6.1.4.1.37950.1.1.6.2.2.8.28.1.4
		priPMQTTUserNameS OBJECT-TYPE
			SYNTAX OCTET STRING
			MAX-ACCESS read-write
			STATUS current
			DESCRIPTION
				"Description."
			::= { priPMQTTEntry 4 }

		
--  1.3.6.1.4.1.37950.1.1.6.2.2.8.28.1.5
		-- 1.3.6.1.4.1.37950.1.1.6.2.2.8.28.1.5
		priPMQTTPasswordS OBJECT-TYPE
			SYNTAX OCTET STRING
			MAX-ACCESS read-write
			STATUS current
			DESCRIPTION
				"Description."
			::= { priPMQTTEntry 5 }

		
--  1.3.6.1.4.1.37950.1.1.6.2.2.8.28.1.6
		-- 1.3.6.1.4.1.37950.1.1.6.2.2.8.28.1.6
		priPMQTTIDS OBJECT-TYPE
			SYNTAX OCTET STRING
			MAX-ACCESS read-write
			STATUS current
			DESCRIPTION
				"Description."
			::= { priPMQTTEntry 6 }

		
		-- 1.3.6.1.4.1.37950.1.1.6.2.2.8.29
		priPAPTable OBJECT-TYPE
			SYNTAX SEQUENCE OF PriPAPEntry
			MAX-ACCESS not-accessible
			STATUS current
			DESCRIPTION
				"Description."
			::= { v1600gPriPShow 29 }

		
		-- 1.3.6.1.4.1.37950.1.1.6.2.2.8.29.1
		priPAPEntry OBJECT-TYPE
			SYNTAX PriPAPEntry
			MAX-ACCESS not-accessible
			STATUS current
			DESCRIPTION
				"Description."
			INDEX { priPAPPIDS }
			::= { priPAPTable 1 }

		
		PriPAPEntry ::=
			SEQUENCE { 
				priPAPPIDS
					INTEGER,
				priPAPStatusS
					INTEGER,
				priPAPVLANS
					Integer32
			 }

		-- 1.3.6.1.4.1.37950.1.1.6.2.2.8.29.1.1
		priPAPPIDS OBJECT-TYPE
			SYNTAX INTEGER
			MAX-ACCESS read-write
			STATUS current
			DESCRIPTION
				"Description."
			::= { priPAPEntry 1 }

		
		-- 1.3.6.1.4.1.37950.1.1.6.2.2.8.29.1.2
		priPAPStatusS OBJECT-TYPE
			SYNTAX INTEGER
				{
				disable(0),
				enable(1)
				}
			MAX-ACCESS read-write
			STATUS current
			DESCRIPTION
				"Description."
			::= { priPAPEntry 2 }

		
		-- 1.3.6.1.4.1.37950.1.1.6.2.2.8.29.1.3
		priPAPVLANS OBJECT-TYPE
			SYNTAX Integer32
			MAX-ACCESS read-write
			STATUS current
			DESCRIPTION
				"Description."
			::= { priPAPEntry 3 }

		
--  1.3.6.1.4.1.37950.1.1.6.2.2.9
		-- 1.3.6.1.4.1.37950.1.1.6.2.2.9
		v1600gIGMPProfileTable OBJECT-TYPE
			SYNTAX SEQUENCE OF V1600gIGMPProfileEntry
			MAX-ACCESS not-accessible
			STATUS current
			DESCRIPTION
				"Description."
			::= { v1600gProfileShow 9 }

		
--  1.3.6.1.4.1.37950.1.1.6.2.2.9.1
		-- 1.3.6.1.4.1.37950.1.1.6.2.2.9.1
		v1600gIGMPProfileEntry OBJECT-TYPE
			SYNTAX V1600gIGMPProfileEntry
			MAX-ACCESS not-accessible
			STATUS current
			DESCRIPTION
				"Description."
			INDEX { igmpProfileIDS }
			::= { v1600gIGMPProfileTable 1 }

		
		V1600gIGMPProfileEntry ::=
			SEQUENCE { 
				igmpProfileIDS
					Integer32,
				igmpVersionS
					INTEGER,
				igmpModeS
					INTEGER,
				igmpFastLeaveS
					INTEGER,
				igmpNotMatchGroupS
					INTEGER,
				igmpRobustnessS
					Integer32,
				igmpProxyIPS
					OCTET STRING,
				igmpQueryIntervalS
					Unsigned32,
				igmpQueryMaxrespS
					Unsigned32,
				igmpQueryLastIntervalS
					Unsigned32,
				igmpRateLimitS
					Unsigned32
			 }

--  1.3.6.1.4.1.37950.1.1.6.2.2.9.1.1
		-- 1.3.6.1.4.1.37950.1.1.6.2.2.9.1.1
		igmpProfileIDS OBJECT-TYPE
			SYNTAX Integer32
			MAX-ACCESS read-write
			STATUS current
			DESCRIPTION
				"Description."
			::= { v1600gIGMPProfileEntry 1 }

		
--  1.3.6.1.4.1.37950.1.1.6.2.2.9.1.2
		-- 1.3.6.1.4.1.37950.1.1.6.2.2.9.1.2
		igmpVersionS OBJECT-TYPE
			SYNTAX INTEGER
				{
				v1(1),
				v2(2),
				v3(3)
				}
			MAX-ACCESS read-write
			STATUS current
			DESCRIPTION
				"Description."
			::= { v1600gIGMPProfileEntry 2 }

		
--  1.3.6.1.4.1.37950.1.1.6.2.2.9.1.3
		-- 1.3.6.1.4.1.37950.1.1.6.2.2.9.1.3
		igmpModeS OBJECT-TYPE
			SYNTAX INTEGER
				{
				snooping(1),
				spr(2),
				proxy(3),
				flood(4)
				}
			MAX-ACCESS read-write
			STATUS current
			DESCRIPTION
				"Description."
			::= { v1600gIGMPProfileEntry 3 }

		
--  1.3.6.1.4.1.37950.1.1.6.2.2.9.1.4
		-- 1.3.6.1.4.1.37950.1.1.6.2.2.9.1.4
		igmpFastLeaveS OBJECT-TYPE
			SYNTAX INTEGER
				{
				disable(1),
				enable(2)
				}
			MAX-ACCESS read-write
			STATUS current
			DESCRIPTION
				"Description."
			::= { v1600gIGMPProfileEntry 4 }

		
--  1.3.6.1.4.1.37950.1.1.6.2.2.9.1.5
		-- 1.3.6.1.4.1.37950.1.1.6.2.2.9.1.5
		igmpNotMatchGroupS OBJECT-TYPE
			SYNTAX INTEGER
				{
				discard(1),
				forward(2)
				}
			MAX-ACCESS read-write
			STATUS current
			DESCRIPTION
				"Description."
			::= { v1600gIGMPProfileEntry 5 }

		
--  1.3.6.1.4.1.37950.1.1.6.2.2.9.1.6
		-- 1.3.6.1.4.1.37950.1.1.6.2.2.9.1.6
		igmpRobustnessS OBJECT-TYPE
			SYNTAX Integer32
			MAX-ACCESS read-write
			STATUS current
			DESCRIPTION
				"Description."
			::= { v1600gIGMPProfileEntry 6 }

		
--  1.3.6.1.4.1.37950.1.1.6.2.2.9.1.7
		-- 1.3.6.1.4.1.37950.1.1.6.2.2.9.1.7
		igmpProxyIPS OBJECT-TYPE
			SYNTAX OCTET STRING
			MAX-ACCESS read-write
			STATUS current
			DESCRIPTION
				"Description."
			::= { v1600gIGMPProfileEntry 7 }

		
--  1.3.6.1.4.1.37950.1.1.6.2.2.9.1.8
		-- 1.3.6.1.4.1.37950.1.1.6.2.2.9.1.8
		igmpQueryIntervalS OBJECT-TYPE
			SYNTAX Unsigned32
			MAX-ACCESS read-write
			STATUS current
			DESCRIPTION
				"Description."
			::= { v1600gIGMPProfileEntry 8 }

		
--  1.3.6.1.4.1.37950.1.1.6.2.2.9.1.9
		-- 1.3.6.1.4.1.37950.1.1.6.2.2.9.1.9
		igmpQueryMaxrespS OBJECT-TYPE
			SYNTAX Unsigned32
			MAX-ACCESS read-write
			STATUS current
			DESCRIPTION
				"Description."
			::= { v1600gIGMPProfileEntry 9 }

		
--  1.3.6.1.4.1.37950.1.1.6.2.2.9.1.10
		-- 1.3.6.1.4.1.37950.1.1.6.2.2.9.1.10
		igmpQueryLastIntervalS OBJECT-TYPE
			SYNTAX Unsigned32
			MAX-ACCESS read-write
			STATUS current
			DESCRIPTION
				"Description."
			::= { v1600gIGMPProfileEntry 10 }

		
--  1.3.6.1.4.1.37950.1.1.6.2.2.9.1.11
		-- 1.3.6.1.4.1.37950.1.1.6.2.2.9.1.11
		igmpRateLimitS OBJECT-TYPE
			SYNTAX Unsigned32
			MAX-ACCESS read-write
			STATUS current
			DESCRIPTION
				"Description."
			::= { v1600gIGMPProfileEntry 11 }

		
--  1.3.6.1.4.1.37950.1.1.6.2.2.10
		-- 1.3.6.1.4.1.37950.1.1.6.2.2.10
		v1600gFormatProfileTable OBJECT IDENTIFIER ::= { v1600gProfileShow 10 }

		
--  1.3.6.1.4.1.37950.1.1.6.2.2.10.1
		-- 1.3.6.1.4.1.37950.1.1.6.2.2.10.1
		fmtPSwitchTable OBJECT-TYPE
			SYNTAX SEQUENCE OF FmtPSwitchEntry
			MAX-ACCESS not-accessible
			STATUS current
			DESCRIPTION
				"Description."
			::= { v1600gFormatProfileTable 1 }

		
--  1.3.6.1.4.1.37950.1.1.6.2.2.10.1.1
		-- 1.3.6.1.4.1.37950.1.1.6.2.2.10.1.1
		fmtPSwitchEntry OBJECT-TYPE
			SYNTAX FmtPSwitchEntry
			MAX-ACCESS not-accessible
			STATUS current
			DESCRIPTION
				"Description."
			INDEX { fmtPSwitchProfileIdS }
			::= { fmtPSwitchTable 1 }

		
		FmtPSwitchEntry ::=
			SEQUENCE { 
				fmtPSwitchProfileIdS
					Integer32,
				fmtPOpt82S
					INTEGER,
				fmtPOpt18S
					INTEGER,
				fmtPOpt37S
					INTEGER,
				fmtPPppoePlusS
					INTEGER
			 }

--  1.3.6.1.4.1.37950.1.1.6.2.2.10.1.1.1
		-- 1.3.6.1.4.1.37950.1.1.6.2.2.10.1.1.1
		fmtPSwitchProfileIdS OBJECT-TYPE
			SYNTAX Integer32
			MAX-ACCESS read-write
			STATUS current
			DESCRIPTION
				"Description."
			::= { fmtPSwitchEntry 1 }

		
--  1.3.6.1.4.1.37950.1.1.6.2.2.10.1.1.2
		-- 1.3.6.1.4.1.37950.1.1.6.2.2.10.1.1.2
		fmtPOpt82S OBJECT-TYPE
			SYNTAX INTEGER
				{
				disable(0),
				enable(1)
				}
			MAX-ACCESS read-write
			STATUS current
			DESCRIPTION
				"Description."
			::= { fmtPSwitchEntry 2 }

		
--  1.3.6.1.4.1.37950.1.1.6.2.2.10.1.1.3
		-- 1.3.6.1.4.1.37950.1.1.6.2.2.10.1.1.3
		fmtPOpt18S OBJECT-TYPE
			SYNTAX INTEGER
				{
				disable(0),
				enable(1)
				}
			MAX-ACCESS read-write
			STATUS current
			DESCRIPTION
				"Description."
			::= { fmtPSwitchEntry 3 }

		
--  1.3.6.1.4.1.37950.1.1.6.2.2.10.1.1.4
		-- 1.3.6.1.4.1.37950.1.1.6.2.2.10.1.1.4
		fmtPOpt37S OBJECT-TYPE
			SYNTAX INTEGER
				{
				disable(0),
				enable(1)
				}
			MAX-ACCESS read-write
			STATUS current
			DESCRIPTION
				"Description."
			::= { fmtPSwitchEntry 4 }

		
--  1.3.6.1.4.1.37950.1.1.6.2.2.10.1.1.5
		-- 1.3.6.1.4.1.37950.1.1.6.2.2.10.1.1.5
		fmtPPppoePlusS OBJECT-TYPE
			SYNTAX INTEGER
				{
				disable(0),
				enable(1)
				}
			MAX-ACCESS read-write
			STATUS current
			DESCRIPTION
				"Description."
			::= { fmtPSwitchEntry 5 }

		
--  1.3.6.1.4.1.37950.1.1.6.2.2.10.2
		-- 1.3.6.1.4.1.37950.1.1.6.2.2.10.2
		fmtPTypeTable OBJECT-TYPE
			SYNTAX SEQUENCE OF FmtPTypeEntry
			MAX-ACCESS not-accessible
			STATUS current
			DESCRIPTION
				"Description."
			::= { v1600gFormatProfileTable 2 }

		
--  1.3.6.1.4.1.37950.1.1.6.2.2.10.2.1
		-- 1.3.6.1.4.1.37950.1.1.6.2.2.10.2.1
		fmtPTypeEntry OBJECT-TYPE
			SYNTAX FmtPTypeEntry
			MAX-ACCESS not-accessible
			STATUS current
			DESCRIPTION
				"Description."
			INDEX { fmtPTypeProfileIdS }
			::= { fmtPTypeTable 1 }

		
		FmtPTypeEntry ::=
			SEQUENCE { 
				fmtPTypeProfileIdS
					Integer32,
				formatPTypeS
					INTEGER
			 }

--  1.3.6.1.4.1.37950.1.1.6.2.2.10.2.1.1
		-- 1.3.6.1.4.1.37950.1.1.6.2.2.10.2.1.1
		fmtPTypeProfileIdS OBJECT-TYPE
			SYNTAX Integer32
			MAX-ACCESS read-write
			STATUS current
			DESCRIPTION
				"Description."
			::= { fmtPTypeEntry 1 }

		
--  1.3.6.1.4.1.37950.1.1.6.2.2.10.2.1.2
		-- 1.3.6.1.4.1.37950.1.1.6.2.2.10.2.1.2
		formatPTypeS OBJECT-TYPE
			SYNTAX INTEGER
				{
				custom(0),
				ctc(1),
				unicom(2)
				}
			MAX-ACCESS read-write
			STATUS current
			DESCRIPTION
				"Description."
			::= { fmtPTypeEntry 2 }

		
--  1.3.6.1.4.1.37950.1.1.6.2.2.10.3
		-- 1.3.6.1.4.1.37950.1.1.6.2.2.10.3
		fmtPIdTable OBJECT-TYPE
			SYNTAX SEQUENCE OF FmtPIdEntry
			MAX-ACCESS not-accessible
			STATUS current
			DESCRIPTION
				"Description."
			::= { v1600gFormatProfileTable 3 }

		
--  1.3.6.1.4.1.37950.1.1.6.2.2.10.3.1
		-- 1.3.6.1.4.1.37950.1.1.6.2.2.10.3.1
		fmtPIdEntry OBJECT-TYPE
			SYNTAX FmtPIdEntry
			MAX-ACCESS not-accessible
			STATUS current
			DESCRIPTION
				"Description."
			INDEX { fmtPIdProfileIdS }
			::= { fmtPIdTable 1 }

		
		FmtPIdEntry ::=
			SEQUENCE { 
				fmtPIdProfileIdS
					Integer32,
				fmtPIdCircuitIdStr
					OCTET STRING,
				fmtPIdRemoteIdStr
					OCTET STRING
			 }

--  1.3.6.1.4.1.37950.1.1.6.2.2.10.3.1.1
		-- 1.3.6.1.4.1.37950.1.1.6.2.2.10.3.1.1
		fmtPIdProfileIdS OBJECT-TYPE
			SYNTAX Integer32
			MAX-ACCESS read-write
			STATUS current
			DESCRIPTION
				"Description."
			::= { fmtPIdEntry 1 }

		
--  1.3.6.1.4.1.37950.1.1.6.2.2.10.3.1.2
		-- 1.3.6.1.4.1.37950.1.1.6.2.2.10.3.1.2
		fmtPIdCircuitIdStr OBJECT-TYPE
			SYNTAX OCTET STRING
			MAX-ACCESS read-write
			STATUS current
			DESCRIPTION
				"Description."
			::= { fmtPIdEntry 2 }

		
--  1.3.6.1.4.1.37950.1.1.6.2.2.10.3.1.3
		-- 1.3.6.1.4.1.37950.1.1.6.2.2.10.3.1.3
		fmtPIdRemoteIdStr OBJECT-TYPE
			SYNTAX OCTET STRING
			MAX-ACCESS read-write
			STATUS current
			DESCRIPTION
				"Description."
			::= { fmtPIdEntry 3 }

		
--  1.3.6.1.4.1.37950.1.1.6.2.2.10.4
		-- 1.3.6.1.4.1.37950.1.1.6.2.2.10.4
		fmtPNameTable OBJECT-TYPE
			SYNTAX SEQUENCE OF FmtPNameEntry
			MAX-ACCESS not-accessible
			STATUS current
			DESCRIPTION
				"Description."
			::= { v1600gFormatProfileTable 4 }

		
--  1.3.6.1.4.1.37950.1.1.6.2.2.10.4.1
		-- 1.3.6.1.4.1.37950.1.1.6.2.2.10.4.1
		fmtPNameEntry OBJECT-TYPE
			SYNTAX FmtPNameEntry
			MAX-ACCESS not-accessible
			STATUS current
			DESCRIPTION
				"Description."
			INDEX { fmtPNamePId }
			::= { fmtPNameTable 1 }

		
		FmtPNameEntry ::=
			SEQUENCE { 
				fmtPNamePId
					Integer32,
				fmtPNameTableName
					OCTET STRING
			 }

--  1.3.6.1.4.1.37950.1.1.6.2.2.10.4.1.1
		-- 1.3.6.1.4.1.37950.1.1.6.2.2.10.4.1.1
		fmtPNamePId OBJECT-TYPE
			SYNTAX Integer32
			MAX-ACCESS read-write
			STATUS current
			DESCRIPTION
				"Description."
			::= { fmtPNameEntry 1 }

		
--  1.3.6.1.4.1.37950.1.1.6.2.2.10.4.1.2
		-- 1.3.6.1.4.1.37950.1.1.6.2.2.10.4.1.2
		fmtPNameTableName OBJECT-TYPE
			SYNTAX OCTET STRING
			MAX-ACCESS read-write
			STATUS current
			DESCRIPTION
				"Description."
			::= { fmtPNameEntry 2 }

		
--  1.3.6.1.4.1.37950.1.1.6.2.2.11
		-- 1.3.6.1.4.1.37950.1.1.6.2.2.11
		v1600gIGMPPNameTable OBJECT-TYPE
			SYNTAX SEQUENCE OF V1600gIGMPPNameEntry
			MAX-ACCESS not-accessible
			STATUS current
			DESCRIPTION
				"Description."
			::= { v1600gProfileShow 11 }

		
--  1.3.6.1.4.1.37950.1.1.6.2.2.11.1
		-- 1.3.6.1.4.1.37950.1.1.6.2.2.11.1
		v1600gIGMPPNameEntry OBJECT-TYPE
			SYNTAX V1600gIGMPPNameEntry
			MAX-ACCESS not-accessible
			STATUS current
			DESCRIPTION
				"Description."
			INDEX { igmpPNamePId }
			::= { v1600gIGMPPNameTable 1 }

		
		V1600gIGMPPNameEntry ::=
			SEQUENCE { 
				igmpPNamePId
					Integer32,
				igmpPNameTableName
					OCTET STRING
			 }

--  1.3.6.1.4.1.37950.1.1.6.2.2.11.1.1
		-- 1.3.6.1.4.1.37950.1.1.6.2.2.11.1.1
		igmpPNamePId OBJECT-TYPE
			SYNTAX Integer32
			MAX-ACCESS read-write
			STATUS current
			DESCRIPTION
				"Description."
			::= { v1600gIGMPPNameEntry 1 }

		
--  1.3.6.1.4.1.37950.1.1.6.2.2.11.1.2
		-- 1.3.6.1.4.1.37950.1.1.6.2.2.11.1.2
		igmpPNameTableName OBJECT-TYPE
			SYNTAX OCTET STRING
			MAX-ACCESS read-write
			STATUS current
			DESCRIPTION
				"Description."
			::= { v1600gIGMPPNameEntry 2 }

		
--  1.3.6.1.4.1.37950.1.1.6.2.2.12
		-- 1.3.6.1.4.1.37950.1.1.6.2.2.12
		v1600gxbIGMPProfileTable OBJECT-TYPE
			SYNTAX SEQUENCE OF V1600gxbIGMPProfileEntry
			MAX-ACCESS not-accessible
			STATUS current
			DESCRIPTION
				"Description."
			::= { v1600gProfileShow 12 }

		
--  1.3.6.1.4.1.37950.1.1.6.2.2.12.1
		-- 1.3.6.1.4.1.37950.1.1.6.2.2.12.1
		v1600gxbIGMPProfileEntry OBJECT-TYPE
			SYNTAX V1600gxbIGMPProfileEntry
			MAX-ACCESS not-accessible
			STATUS current
			DESCRIPTION
				"Description."
			INDEX { gxbIgmpProfileIDS }
			::= { v1600gxbIGMPProfileTable 1 }

		
		V1600gxbIGMPProfileEntry ::=
			SEQUENCE { 
				gxbIgmpProfileIDS
					Integer32,
				gxbIgmpVersionS
					INTEGER,
				gxbIgmpModeS
					INTEGER,
				gxbIgmpFastLeaveS
					INTEGER,
				gxbIgmpUpstreamTagControlS
					INTEGER,
				gxbIgmpUpstreamTciVlanS
					Integer32,
				gxbIgmpUpstreamTciPBitsS
					Integer32,
				gxbIgmpRateLimitS
					Unsigned32,
				gxbIgmpRobustnessS
					Integer32,
				gxbIgmpProxyIPS
					IpAddress,
				gxbIgmpQueryIntervalS
					Unsigned32,
				gxbIgmpQueryMaxrespS
					Unsigned32,
				gxbIgmpQueryLastIntervalS
					Unsigned32,
				gxbIgmpDownstreamTagControlS
					INTEGER,
				gxbIgmpDownstreamTciVLANS
					Integer32,
				gxbIgmpDownstreamTciPBitsS
					Integer32,
				gxbIgmpNonMatchGroupS
					INTEGER
			 }

--  1.3.6.1.4.1.37950.1.1.6.2.2.12.1.1
		-- 1.3.6.1.4.1.37950.1.1.6.2.2.12.1.1
		gxbIgmpProfileIDS OBJECT-TYPE
			SYNTAX Integer32
			MAX-ACCESS read-write
			STATUS current
			DESCRIPTION
				"Description."
			::= { v1600gxbIGMPProfileEntry 1 }

		
--  1.3.6.1.4.1.37950.1.1.6.2.2.12.1.2
		-- 1.3.6.1.4.1.37950.1.1.6.2.2.12.1.2
		gxbIgmpVersionS OBJECT-TYPE
			SYNTAX INTEGER
				{
				igmp_v1(1),
				igmp_v2(2),
				igmp_v3(3),
				mld_v1(16),
				mld_v2(17)
				}
			MAX-ACCESS read-write
			STATUS current
			DESCRIPTION
				"Description."
			::= { v1600gxbIGMPProfileEntry 2 }

		
--  1.3.6.1.4.1.37950.1.1.6.2.2.12.1.3
		-- 1.3.6.1.4.1.37950.1.1.6.2.2.12.1.3
		gxbIgmpModeS OBJECT-TYPE
			SYNTAX INTEGER
				{
				snooping(0),
				spr(1),
				proxy(2)
				}
			MAX-ACCESS read-write
			STATUS current
			DESCRIPTION
				"Description."
			::= { v1600gxbIGMPProfileEntry 3 }

		
--  1.3.6.1.4.1.37950.1.1.6.2.2.12.1.4
		-- 1.3.6.1.4.1.37950.1.1.6.2.2.12.1.4
		gxbIgmpFastLeaveS OBJECT-TYPE
			SYNTAX INTEGER
				{
				disable(0),
				enable(1)
				}
			MAX-ACCESS read-write
			STATUS current
			DESCRIPTION
				"Description."
			::= { v1600gxbIGMPProfileEntry 4 }

		
--  1.3.6.1.4.1.37950.1.1.6.2.2.12.1.5
		-- 1.3.6.1.4.1.37950.1.1.6.2.2.12.1.5
		gxbIgmpUpstreamTagControlS OBJECT-TYPE
			SYNTAX INTEGER
				{
				transparent(0),
				add_vlan_tag(1),
				replace_vlan_tag(2),
				replace_vlan_id(3)
				}
			MAX-ACCESS read-write
			STATUS current
			DESCRIPTION
				"Description."
			::= { v1600gxbIGMPProfileEntry 5 }

		
--  1.3.6.1.4.1.37950.1.1.6.2.2.12.1.6
		-- 1.3.6.1.4.1.37950.1.1.6.2.2.12.1.6
		gxbIgmpUpstreamTciVlanS OBJECT-TYPE
			SYNTAX Integer32
			MAX-ACCESS read-write
			STATUS current
			DESCRIPTION
				"Description."
			::= { v1600gxbIGMPProfileEntry 6 }

		
--  1.3.6.1.4.1.37950.1.1.6.2.2.12.1.7
		-- 1.3.6.1.4.1.37950.1.1.6.2.2.12.1.7
		gxbIgmpUpstreamTciPBitsS OBJECT-TYPE
			SYNTAX Integer32
			MAX-ACCESS read-write
			STATUS current
			DESCRIPTION
				"Description."
			::= { v1600gxbIGMPProfileEntry 7 }

		
--  1.3.6.1.4.1.37950.1.1.6.2.2.12.1.8
		-- 1.3.6.1.4.1.37950.1.1.6.2.2.12.1.8
		gxbIgmpRateLimitS OBJECT-TYPE
			SYNTAX Unsigned32
			MAX-ACCESS read-write
			STATUS current
			DESCRIPTION
				"Description."
			::= { v1600gxbIGMPProfileEntry 8 }

		
--  1.3.6.1.4.1.37950.1.1.6.2.2.12.1.9
		-- 1.3.6.1.4.1.37950.1.1.6.2.2.12.1.9
		gxbIgmpRobustnessS OBJECT-TYPE
			SYNTAX Integer32
			MAX-ACCESS read-write
			STATUS current
			DESCRIPTION
				"Description."
			::= { v1600gxbIGMPProfileEntry 9 }

		
--  1.3.6.1.4.1.37950.1.1.6.2.2.12.1.10
		-- 1.3.6.1.4.1.37950.1.1.6.2.2.12.1.10
		gxbIgmpProxyIPS OBJECT-TYPE
			SYNTAX IpAddress
			MAX-ACCESS read-write
			STATUS current
			DESCRIPTION
				"Description."
			::= { v1600gxbIGMPProfileEntry 10 }

		
--  1.3.6.1.4.1.37950.1.1.6.2.2.12.1.11
		-- 1.3.6.1.4.1.37950.1.1.6.2.2.12.1.11
		gxbIgmpQueryIntervalS OBJECT-TYPE
			SYNTAX Unsigned32
			MAX-ACCESS read-write
			STATUS current
			DESCRIPTION
				"Description."
			::= { v1600gxbIGMPProfileEntry 11 }

		
--  1.3.6.1.4.1.37950.1.1.6.2.2.12.1.12
		-- 1.3.6.1.4.1.37950.1.1.6.2.2.12.1.12
		gxbIgmpQueryMaxrespS OBJECT-TYPE
			SYNTAX Unsigned32
			MAX-ACCESS read-write
			STATUS current
			DESCRIPTION
				"Description."
			::= { v1600gxbIGMPProfileEntry 12 }

		
--  1.3.6.1.4.1.37950.1.1.6.2.2.12.1.13
		-- 1.3.6.1.4.1.37950.1.1.6.2.2.12.1.13
		gxbIgmpQueryLastIntervalS OBJECT-TYPE
			SYNTAX Unsigned32
			MAX-ACCESS read-write
			STATUS current
			DESCRIPTION
				"Description."
			::= { v1600gxbIGMPProfileEntry 13 }

		
--  1.3.6.1.4.1.37950.1.1.6.2.2.12.1.14
		-- 1.3.6.1.4.1.37950.1.1.6.2.2.12.1.14
		gxbIgmpDownstreamTagControlS OBJECT-TYPE
			SYNTAX INTEGER
				{
				transparent(0),
				strip_outer_tag(1),
				add_outer_tag(2),
				replace_outer_tci(3),
				replace_outer_vid(4),
				add_outer_tag_by_subscriber_conf_info(5),
				replace_outer_tci_by_subscriber_conf_info(6),
				replace_outer_vid_by_subscriber_conf_info(7)
				}
			MAX-ACCESS read-write
			STATUS current
			DESCRIPTION
				"Description."
			::= { v1600gxbIGMPProfileEntry 14 }

		
--  1.3.6.1.4.1.37950.1.1.6.2.2.12.1.15
		-- 1.3.6.1.4.1.37950.1.1.6.2.2.12.1.15
		gxbIgmpDownstreamTciVLANS OBJECT-TYPE
			SYNTAX Integer32
			MAX-ACCESS read-write
			STATUS current
			DESCRIPTION
				"Description."
			::= { v1600gxbIGMPProfileEntry 15 }

		
--  1.3.6.1.4.1.37950.1.1.6.2.2.12.1.16
		-- 1.3.6.1.4.1.37950.1.1.6.2.2.12.1.16
		gxbIgmpDownstreamTciPBitsS OBJECT-TYPE
			SYNTAX Integer32
			MAX-ACCESS read-write
			STATUS current
			DESCRIPTION
				"Description."
			::= { v1600gxbIGMPProfileEntry 16 }

		
--  1.3.6.1.4.1.37950.1.1.6.2.2.12.1.17
		-- 1.3.6.1.4.1.37950.1.1.6.2.2.12.1.17
		gxbIgmpNonMatchGroupS OBJECT-TYPE
			SYNTAX INTEGER
				{
				discard(0),
				forward(1)
				}
			MAX-ACCESS read-write
			STATUS current
			DESCRIPTION
				"Description."
			::= { v1600gxbIGMPProfileEntry 17 }

		
	
	END

--
-- V1600G.my
--
